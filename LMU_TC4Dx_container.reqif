# Specification: Specification Document

## METADATA: Metadata
| id | value |
| --- | --- |
- Object type: Information

## R2: Local Memory Unit (LMU)
Local Memory Unit (LMU)
The local memory unit is a resource attached to the System Resource Interconnect (SRI) that provides SRAM for general purpose use. A product may contain multiple instances of the LMU, and each instance has its own set of configuration registers.
Data stored in the SRAM is protected by error-correcting codes (ECC). Master access to areas of each LMU can be permitted or denied by configuring up to 16 address ranges using an Access Protection Unit (APU) in the LMU. The ranges can be sized in 64-byte increments and the master agent functions can be granted access for read and write independently. A master agent function is identified by its number (ID), Protection Register Set (PRS) and Virtual Machine (VM) identifier.
Note: Please refer to the system address map for the availability of LMU instances in a specific product.
- Object ID: TQJA-EDJE-GEIE-FGFB
- Object type: Information

### R3: Feature list
Feature list
- Each LMU instance has 512 KiB of SRAM
- Provides byte, half-word, word, and double-word accesses, as well as double-word burst transactions of length 2,4, or 8 to SRAM
- Provides word and double-word access to most configuration registers
- Each LMU has sixteen Access Protection Units (APUs) for memory access protection
- Object ID: EQHA-EDJE-GFCA-HBHH
- Object type: Information

### R4: Functional overview
Functional overview
The LMU SRAM can be used for code execution, data storage or overlay memory. The address range of the memory for each LMU instance is defined in the system memory map. The memory supports being aliased to more than one address range, for example, cached and non-cached segments. A block diagram of the LMU is shown below.
Access to the SRAM is protected by 16 Access Protection Units (APUs), each of which can be configured to limit access by masters to a configurable memory range. By default (after reset), read access is allowed by any master to the whole memory and write access is restricted to certain masters, details of which can be found in the reset value of RGNx_ACCEN_WRA. The safety configuration and monitoring registers are protected by PROTSE.
The memory implements memory integrity checking for error detection and correction. This means that the memory must be initialized before reading with the integrity checking enabled to avoid generating spurious data corruption errors. Initializing with the memory integrity logic disabled allows the LMU SRAM to support initialization using word (32-bit) or smaller writes. Initialization using 64-bit writes is always possible.
If memory integrity checking is enabled, a read access which fails the integrity check will cause an error condition to be flagged to the initiating bus master. This behavior can be changed by setting the MEMCON.ERRDIS bit to 1 B. If ERRDIS is set, the access will terminate without an integrity error being reported to the SRI. The ERRDIS bit-field of the MEMCON register is protected by the MEMCON.ERRDISWE bit. If the data written to the register has the MEMCON.ERRDISWE bit set to 0 B, no change will be made to ERRDIS regardless of the data written to the field.
An alarm will be triggered whenever there is an ECC error, regardless of the value of MEMCON.ERRDIS.
The SRAM can be written as a 64-bit memory without using internal Read-Modify-Write (iRMW) operations. Any write access of less than 64 bits of data results in an iRMW operation to correctly write the data and update the ECC data. This happens transparently to the rest of the system unless an uncorrected ECC error is detected during the read phase of the iRMW. Any such ECC error will be flagged with an alarm in the same way as a data ECC error occurring during a normal read. In addition, the MEMCON.RMWERR flag will be set. The write operation will not take place as this would write potentially incorrect data to the memory.
LMU block diagram
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- Object ID: PLDA-EDJE-GFCA-HGAH
- Object type: Information
- CrossRefLink -> R18
- CrossRefLink -> R14
- CrossRefLink -> R15
- CrossRefLink -> R15
- CrossRefLink -> R15
- CrossRefLink -> R15
- CrossRefLink -> R15
- CrossRefLink -> R15

### R5: Functional description
Functional description
The following sections describe the functions of the LMU.
- Object ID: SQIA-EIEI-EBJH-BFDD
- Object type: Information

#### R6: Memory protection
Memory protection
The LMU allows for the definition of 16 protected regions of SRAM memory defined by an array of access protection unit (APU) instances. This protection applies only to accesses to SRAM included in the LMU, not to registers.
The configuration of the protection regions is held in the set of registers named with the prefix RGNx_, where x is the number of the APU instance. After reset, the protection region range registers will be set to include the whole of the LMU SRAM address space, and read access by all masters will be enabled but write access is restricted to CPU0 and Cerberus. If overlapping regions are defined, then an access only needs to be permitted by one of the overlapping regions for it to succeed.
An APU can only be configured by writing to the equivalent shadow register in the set named with the prefix ACCENCFG_. The shadow register set is protected by a mechanism controlled by the PROTRGN register. The SEL field in this register selects which region is to be configured and write access to the shadow registers is only given when the PROTRGN.STATE field is in an unlocked state. For full details of how the protection mechanism operates, see the access protection section of the manual.
If the access protection is violated by a read access, the LMU will trigger an APU alarm and cause an SRI error on the data phase. If the access protection is violated by a write access, the LMU will trigger an APU alarm and inhibit the write to the SRAM.
In the case of an SRI RMW access, the APU checks for both the read and the write part of the access are done in the address phase of the read part. If either the read or write part would violate the access protection then the LMU will trigger an APU alarm and cause an SRI error on the read data phase.
- Object ID: FBJA-EDJE-GEIF-AJHJ
- Object type: Information
- CrossRefLink -> R17
- CrossRefLink -> R17

#### R7: Register protection
Register protection
The registers that control and monitor safety mechanisms are protected by the PROTSE register. Write access to these registers is only given when the PROTSE.STATE field is in an unlocked state.
Any access to an address in the configuration register space of the LMU that is not to a defined register will cause an SRI error which will trigger an alarm in the SRI. Any access to an SFR that does not comply with the access mode for that SFR will cause an SRI error, which will trigger an alarm in the SRI. Any access to the PROTSE or PROTRGN registers that violates the PROT register access rules will trigger an APU alarm.
- Object ID: NAAA-EDJE-GEIF-AGIA
- Object type: Information
- CrossRefLink -> R14
- CrossRefLink -> R14
- CrossRefLink -> R14
- CrossRefLink -> R17

#### R8: Clock control
Clock control
The LMU contains power saving logic that only clocks the SRAM and other functions when an access is being performed.
- Object ID: CGMA-EDJE-GEIF-IBII
- Object type: Information

#### R9: Power down behavior
Power down behavior
Some instances of the LMU have the ability to power down their SRAM which is controlled by the power management system (PMS). When an LMU instance is powered down it will respond to any access to its SRI interface with an SRI error which will trigger an alarm in the SRI.
- Object ID: XUAA-FCEA-FEFH-IBHJ
- Object type: Information

### R10: Registers
Registers
The registers in the LMU are accessible using 32-bit-and 64-bit SRI read and write transactions, except where documented as 32-bit only in the register overview table.
- Object ID: EMNA-EHHJ-HFDI-HGBG
- Object type: Information

#### R11: Register overview - access mode glossary
Register overview - access mode glossary
Register overview - access mode glossary
| Keyword | Description |
| --- | --- |
| RGN | Access protection using PROT register . |
| SE | Access protection using PROT register . |
| 32 | Description can be found in global access mode definition. |
| BE | Description can be found in global access mode definition. |
| SV | Description can be found in global access mode definition. |
| PROT | Description can be found in global access mode definition. |
| U | Description can be found in global access mode definition. |
- Object ID: refid_AURIXTC4XX_B_IFX_ATVMC_CE_LMU_100_generic_LMU_Access_mode_all
- Object type: Information

#### R12
Registers overview - LMU (ascending offset address)
Registers overview - LMU (ascending offset address)
| Short name | Long name | Offset address | Access mode |  | Reset | See |
| --- | --- | --- | --- | --- | --- | --- |
| Short name | Long name | Offset address | Read | Write | Reset | See |
| ID | Module identification register | 00008 H | 32 | BE | PowerOn Reset | Module identification register |
| PROTSE | Protection for safety registers | 00028 H | 32 | SV, 32, PROT | Application Reset | Protection for safety registers |
| MEMCON | Memory control register | 00060 H | 32 | SV, SE, 32 | Application Reset | Memory control register |
| SCTRL | Safety control register | 00064 H | 32 | SV, SE, 32 | Application Reset | Safety control register |
| PROTRGN | Protection for memory regions | 00070 H | 32 | SV, 32, PROT | Application Reset | Protection for memory regions |
| RGNx_ACCEN_WRA | Region write access enable register A | 00080 H+x*20 H | U | BE | Application Reset | Region write access enable register A |
| RGNx_ACCEN_WRB | Region write access enable register B | 00084 H+x*20 H | U | BE | Application Reset | Region write access enable register B |
| RGNx_ACCEN_RDA | Region read access enable register A | 00088 H+x*20 H | U | BE | Application Reset | Region read access enable register A |
| RGNx_ACCEN_RDB | Region read access enable register B | 0008C H+x*20 H | U | BE | Application Reset | Region read access enable register B |
| RGNx_ACCEN_VM | Region VM access enable register | 00090 H+x*20 H | U | BE | Application Reset | Region VM access enable register |
| RGNx_ACCEN_PRS | Region PRS access enable register | 00094 H+x*20 H | U | BE | Application Reset | Region PRS access enable register |
| RGNx_ACCEN_RGNLA | Region lower address register | 00098 H+x*20 H | U | BE | Application Reset | Region lower address register |
| RGNx_ACCEN_RGNUA | Region upper address register | 0009C H+x*20 H | U | BE | Application Reset | Region upper address register |
| ACCENCFG_WRA | Configure region write access enable register A | 00300 H | U | RGN, SV | Application Reset | Configure region write access enable register A |
| ACCENCFG_WRB | Configure region write access enable register B | 00304 H | U | RGN, SV | Application Reset | Configure region write access enable register B |
| ACCENCFG_RDA | Configure region read access enable register A | 00308 H | U | RGN, SV | Application Reset | Configure region read access enable register A |
| ACCENCFG_RDB | Configure region read access enable register B | 0030C H | U | RGN, SV | Application Reset | Configure region read access enable register B |
| ACCENCFG_VM | Configure region VM access enable register | 00310 H | U | RGN, SV | Application Reset | Configure region VM access enable register |
| ACCENCFG_PRS | Configure region PRS access enable register | 00314 H | U | RGN, SV | Application Reset | Configure region PRS access enable register |
| ACCENCFG_RGNLA | Configure region lower address register | 00318 H | U | RGN, SV | Application Reset | Configure region lower address register |
| ACCENCFG_RGNUA | Configure region upper address register | 0031C H | U | RGN, SV | Application Reset | Configure region upper address register |
- Object ID: refid_AURIXTC4XX_B_IFX_ATVMC_CE_LMU_100_generic_ROTable7_LMU
- Object type: Information
- CrossRefLink -> R13
- CrossRefLink -> R14
- CrossRefLink -> R15
- CrossRefLink -> R16
- CrossRefLink -> R17
- CrossRefLink -> R18
- CrossRefLink -> R19
- CrossRefLink -> R20
- CrossRefLink -> R21
- CrossRefLink -> R22
- CrossRefLink -> R23
- CrossRefLink -> R24
- CrossRefLink -> R25
- CrossRefLink -> R26
- CrossRefLink -> R27
- CrossRefLink -> R28
- CrossRefLink -> R29
- CrossRefLink -> R30
- CrossRefLink -> R31
- CrossRefLink -> R32
- CrossRefLink -> R33

#### R13: Module identification register
Module identification register
| ID Size: 32 bits | Offset address: | 00008 H |
| --- | --- | --- |
| Module identification register | PowerOn Reset value: | 0088 C005 H |
| 31 | 30 | 29 | 28 | 27 | 26 | 25 | 24 | 23 | 22 | 21 | 20 | 19 | 18 | 17 | 16 |
| --- | --- | --- | --- | --- | --- | --- | --- | --- | --- | --- | --- | --- | --- | --- | --- |
| MOD_NUM |  |  |  |  |  |  |  |  |  |  |  |  |  |  |  |
| r |  |  |  |  |  |  |  |  |  |  |  |  |  |  |  |
| 15 | 14 | 13 | 12 | 11 | 10 | 9 | 8 | 7 | 6 | 5 | 4 | 3 | 2 | 1 | 0 |
| MOD_TYPE |  |  |  |  |  |  |  | MOD_REV |  |  |  |  |  |  |  |
| r |  |  |  |  |  |  |  | r |  |  |  |  |  |  |  |
| Field | Bits | Type | Description |
| --- | --- | --- | --- |
| MOD_REV | 7:0 | r | Module Revision Indicates the revision number of the implementation. This information depends on the design step. |
| MOD_TYPE | 15:8 | r | Module Type This internal marker is fixed to C0 H. |
| MOD_NUM | 31:16 | r | Module Number Indicates the module identification number (0088 H = LMU). |
- Object ID: id_AURIXTC4XX_B_IFX_ATVMC_CE_LMU_100_generic_Register_ID_10634
- Object type: RegisterDefinition

#### R14: Protection for safety registers
Protection for safety registers
The resource protection register allows the definition of a specific PROT owner, and allows the PROT owner and in some PROT states, the secure master to update the PROT state as described in the PROT mechanism.
| PROTSE Size: 32 bits | Offset address: | 00028 H |
| --- | --- | --- |
| Protection for safety registers | Application Reset value: | 0000 0000 H |
| 31 | 30 | 29 | 28 | 27 | 26 | 25 | 24 | 23 | 22 | 21 | 20 | 19 | 18 | 17 | 16 |
| --- | --- | --- | --- | --- | --- | --- | --- | --- | --- | --- | --- | --- | --- | --- | --- |
| OWEN | ODEF | TAGID |  |  |  |  |  | PRSEN | PRS |  |  | VMEN | VM |  |  |
| w | rw | rw |  |  |  |  |  | rw | rw |  |  | rw | rw |  |  |
| 15 | 14 | 13 | 12 | 11 | 10 | 9 | 8 | 7 | 6 | 5 | 4 | 3 | 2 | 1 | 0 |
| 0 |  |  |  |  |  |  |  |  |  |  |  | SWEN | STATE |  |  |
| r |  |  |  |  |  |  |  |  |  |  |  | w | rwh |  |  |
| Field | Bits | Type | Description |
| --- | --- | --- | --- |
| STATE | 2:0 | rwh | Resource protection state Returns the current PROT state when read. Can be written by the PROT owner or CS master to modify the current PROT state if the state transition is valid in the PROT state diagram. 000 B Init (unlocked state) 001 B Config (unlocked state) 010 B ConfigSec (unlocked state) 011 B CheckSec (locked state) 100 B Run (locked state) 101 B RunSec (locked state) 110 B RunLock (locked state) 111 B RunLock (locked state) |
| SWEN | 3 | w | State write enable Write-enable for the STATE field. Reads always return 0. 0 B Disable: STATE field is not updated 1 B Enable: STATE field is updated by the write |
| VM | 18:16 | rw | Virtual machine definition for PROT owner Defines the VM of the PROT owner. This field is ignored if VMEN=0 B or ODEF=0 B. |
| VMEN | 19 | rw | Virtual machine definition enable for PROT owner 0 B Disable: VM is not part of PROT owner definition 1 B Enable: VM is part of PROT owner definition |
| PRS | 22:20 | rw | Protection set definition for PROT owner Defines the PRS of the PROT owner. This field is ignored if PRSEN=0 B or ODEF=0 B. |
| PRSEN | 23 | rw | Protection set definition enable for PROT owner 0 B Disable: PRS is not part of PROT owner definition 1 B Enable: PRS is part of PROT owner definition |
| TAGID | 29:24 | rw | TAG-ID definition for PROT owner Defines the TAGID of the PROT owner. This field is ignored if ODEF=0 B. |
| ODEF | 30 | rw | Enable for PROT owner definition 0 B Undefined: Any master can act as PROT owner (TAGID, VMEN, VM, PRSEN, PRS are ignored) 1 B Defined: TAGID, VMEN, VM, PRSEN, PRS define the PROT owner |
| OWEN | 31 | w | Owner write enable Write-enable for the owner fields. Reads always return 0. 0 B Disable: PROT owner fields (ODEF, TAGID, VMEN, VM, PRSEN, PRS) are not updated 1 B Enable: PROT owner fields (ODEF, TAGID, VMEN, VM, PRSEN, PRS) are updated by the write |
| 0 | 15:4 | r | Reserved Read as 0; should be written with 0. |
Access mode restrictions of
sorted by descending priority
| Mode name | Access mode |  | Description |
| --- | --- | --- | --- |
| write 1 to .SWEN | rwh | STATE |  |
| write 1 to .OWEN | rw | ODEF, PRS, PRSEN, TAGID, VM, VMEN |  |
| (default) | r | ODEF, PRS, PRSEN, TAGID, VM, VMEN |  |
| (default) | rh | STATE |  |
- Object ID: id_AURIXTC4XX_B_IFX_ATVMC_CE_LMU_100_generic_Register_PROTSE_10684
- Object type: RegisterDefinition

#### R15: Memory control register
Memory control register
This register allows software to monitor both the memory integrity error checking and the error signalling to the SMU.
| MEMCON Size: 32 bits | Offset address: | 00060 H |
| --- | --- | --- |
| Memory control register | Application Reset value: | 0000 0000 H |
| 31 | 30 | 29 | 28 | 27 | 26 | 25 | 24 | 23 | 22 | 21 | 20 | 19 | 18 | 17 | 16 |
| --- | --- | --- | --- | --- | --- | --- | --- | --- | --- | --- | --- | --- | --- | --- | --- |
| 0 |  |  |  |  |  |  |  |  |  |  |  |  |  |  |  |
| r |  |  |  |  |  |  |  |  |  |  |  |  |  |  |  |
| 15 | 14 | 13 | 12 | 11 | 10 | 9 | 8 | 7 | 6 | 5 | 4 | 3 | 2 | 1 | 0 |
| 0 |  |  |  |  |  | ERRDIS | ERRDISWE | ADDERR | DATAERR | 0 | RMWERR | 0 | INTERR | 0 |  |
| r |  |  |  |  |  | rw | rwh | rwh | rwh | r | rwh | r | rwh | r |  |
| Field | Bits | Type | Description |
| --- | --- | --- | --- |
| INTERR | 2 | rwh | Internal ECC error Flag set by hardware when the LMU detects an ECC error on the internal data path registers while accessing the SRAM. This bit is cleared by writing 0 B but cannot be set by software. 0 B No error has occurred. 1 B An error has been observed during a RAM access. |
| RMWERR | 4 | rwh | Internal read modify write error Flag set by hardware when an uncorrected ECC error is reported by the SRAM on the read phase of an internal RMW operation. This bit is cleared by writing 0 B but cannot be set by software. 0 B No error has occurred. 1 B An error has been observed during an internal RMW operation. |
| DATAERR | 6 | rwh | SRI write data phase ECC error Flag set by hardware when the SRI interface detects an ECC error in the data phase of an incoming write transaction. This bit is cleared by writing 0 B but cannot be set by software. 0 B No error has occurred. 1 B An ECC error has been observed on an SRI transaction addressed to the LMU. |
| ADDERR | 7 | rwh | SRI address phase ECC error Flag set by hardware when the SRI interface detects an ECC error in the address phase of an incoming transaction. This bit is cleared by writing 0 B but cannot be set by software. 0 B No error has occurred. 1 B An ECC address error has been observed on an SRI transaction addressed to the LMU. |
| ERRDISWE | 8 | rwh | ERRDIS write enable Will always return 0 B when read. 0 B Bit Protected: ERRDIS bit remains unchanged after MEMCON write. 1 B ERRDIS bit will be updated by the current write to MEMCON. |
| ERRDIS | 9 | rw | ECC error disable When set to 1B, SRI error reporting of ECC errors in data read from the SRAM will be disabled, and an ECC error on the read phase of an internal RMW will not cause the write phase to be aborted. The value of this bit does not affect the generation of alarms. 0 B Normal behavior. SRI read errors will occur for read transactions with SRAM ECC errors. Default after reset. 1 B Test or initialisation mode. SRI read errors will not be generated on SRAM ECC errors. |
| 0 | 1:0, 3, 5, 31:10 | r | Reserved Read as 0; should be written with 0. |
Access mode restrictions of
sorted by descending priority
| Mode name | Access mode |  | Description |
| --- | --- | --- | --- |
| write 1 to .ERRDISWE | rw | ERRDIS | ERDISS will only be written if ERRDISWE is written with a 1 at the same time |
| (default) | r | ERRDIS | Field can always be read |
- Object ID: id_AURIXTC4XX_B_IFX_ATVMC_CE_LMU_100_generic_Register_MEMCON_60
- Object type: RegisterDefinition

#### R16: Safety control register
Safety control register
This register provides control of the user-configurable safety mechanisms of the LMU.
| SCTRL Size: 32 bits | Offset address: | 00064 H |
| --- | --- | --- |
| Safety control register | Application Reset value: | 0000 0400 H |
| 31 | 30 | 29 | 28 | 27 | 26 | 25 | 24 | 23 | 22 | 21 | 20 | 19 | 18 | 17 | 16 |
| --- | --- | --- | --- | --- | --- | --- | --- | --- | --- | --- | --- | --- | --- | --- | --- |
| 0 |  |  |  |  |  |  |  |  |  |  |  |  |  |  |  |
| r |  |  |  |  |  |  |  |  |  |  |  |  |  |  |  |
| 15 | 14 | 13 | 12 | 11 | 10 | 9 | 8 | 7 | 6 | 5 | 4 | 3 | 2 | 1 | 0 |
| 0 |  |  |  | CMPTST |  | 0 |  |  |  |  |  |  |  |  | GED |
| r |  |  |  | rw |  | r |  |  |  |  |  |  |  |  | w |
| Field | Bits | Type | Description |
| --- | --- | --- | --- |
| GED | 0 | w | Generate error in EDC for data protection The data paths between the SRAM and the LMU SRI interface are protected by error detection code (EDC) logic. This bit is used to inject an error into the EDC code on the next write access so that the EDC check and SMU alarm (internal data transfer EDC error) can be tested. The next write will not be inhibited as a result of this error injection. Reading this bit always returns 0 B. Writing works as follows: 0 B No effect 1 B Inject an error into the LMU data path EDC on the next write access to the LMU. |
| CMPTST | 11:10 | rw | Comparator test Setting this bit-field to ON will inject an error in to the comparators checking the duplicated logic area. This will allow the correct operation of the control redundancy mismatch alarm to be verified. An error will continue to be injected until this field is set to OFF or the module is reset. Writing either of the invalid values (00b or 11b) to this redundantly encoded control field will trigger the control redundancy self-test mismatch alarm allowing it to be tested. 00 B RES0: Invalid 01 B OFF: No error injected 10 B ON: Error injected 11 B RES3: Invalid |
| 0 | 9:1, 31:12 | r | Reserved Read as 0; should be written with 0. |
- Object ID: id_AURIXTC4XX_B_IFX_ATVMC_CE_LMU_100_generic_Register_SCTRL_82
- Object type: RegisterDefinition

#### R17: Protection for memory regions
Protection for memory regions
The resource protection register allows the definition of a specific PROT owner, and allows the PROT owner and in some PROT states, the secure master to update the PROT state as described in the PROT mechanism.
The SEL bit-field is an index into the APU array selecting the APU to be configured.
| PROTRGN Size: 32 bits | Offset address: | 00070 H |
| --- | --- | --- |
| Protection for memory regions | Application Reset value: | 0000 0000 H |
| 31 | 30 | 29 | 28 | 27 | 26 | 25 | 24 | 23 | 22 | 21 | 20 | 19 | 18 | 17 | 16 |
| --- | --- | --- | --- | --- | --- | --- | --- | --- | --- | --- | --- | --- | --- | --- | --- |
| OWEN | ODEF | TAGID |  |  |  |  |  | PRSEN | PRS |  |  | VMEN | VM |  |  |
| w | rw | rw |  |  |  |  |  | rw | rw |  |  | rw | rw |  |  |
| 15 | 14 | 13 | 12 | 11 | 10 | 9 | 8 | 7 | 6 | 5 | 4 | 3 | 2 | 1 | 0 |
| 0 |  |  |  | SEL |  |  |  | 0 |  |  |  | SWEN | STATE |  |  |
| r |  |  |  | rw |  |  |  | r |  |  |  | w | rwh |  |  |
| Field | Bits | Type | Description |
| --- | --- | --- | --- |
| STATE | 2:0 | rwh | Resource protection state Returns the current PROT state when read. Can be written by the PROT owner or CS master to modify the current PROT state if the state transition is valid in the PROT state diagram. 000 B Init (unlocked state) 001 B Config (unlocked state) 010 B ConfigSec (unlocked state) 011 B CheckSec (locked state) 100 B Run (locked state) 101 B RunSec (locked state) 110 B RunLock (locked state) 111 B RunLock (locked state) |
| SWEN | 3 | w | State write enable Write-enable for the STATE field. 0 B Disable: STATE field will not be modified 1 B Enable: STATE field may be modified by the PROT owner |
| SEL | 11:8 | rw | Protection Region Select Selects which set of region protection registers shall be written from the shadow set. |
| VM | 18:16 | rw | Virtual Machine definition for PROT owner Defines the VM of the PROT owner. This field is ignored if VMEN=0 B or ODEF=0 B. |
| VMEN | 19 | rw | Virtual Machine definition Enable for PROT owner 0 B Disable: VM is not part of PROT owner definition 1 B Enable: VM is part of PROT owner definition |
| PRS | 22:20 | rw | Protection Set definition for PROT owner Defines the PRS of the PROT owner. This field is ignored if PRSEN=0 B or ODEF=0 B. |
| PRSEN | 23 | rw | Protection Set definition Enable for PROT owner 0 B Disable: PRS is not part of PROT owner definition 1 B Enable: PRS is part of PROT owner definition |
| TAGID | 29:24 | rw | TAG ID definition for PROT owner Defines the TAGID of the PROT owner. This field is ignored if ODEF=0 B. |
| ODEF | 30 | rw | Enable for PROT owner definition 0 B Undefined: Any master can act as PROT owner (TAGID, VMEN, VM, PRSEN, PRS are ignored) 1 B Defined: TAGID, VMEN, VM, PRSEN, PRS define the PROT owner |
| OWEN | 31 | w | Owner write enable 0 B Disable: PROT owner fields are not modified 1 B Enable: PROT owner fields may be modified by the PROT owner |
| 0 | 7:4, 15:12 | r | Reserved Read as 0; should be written with 0. |
Access mode restrictions of
sorted by descending priority
| Mode name | Access mode |  | Description |
| --- | --- | --- | --- |
| write 1 to .SWEN | rwh | STATE |  |
| write 1 to .OWEN | rw | ODEF, PRS, PRSEN, TAGID, VM, VMEN |  |
| (default) | r | ODEF, PRS, PRSEN, TAGID, VM, VMEN |  |
| (default) | rh | STATE |  |
- Object ID: id_AURIXTC4XX_B_IFX_ATVMC_CE_LMU_100_generic_Register_PROTRGN_10379
- Object type: RegisterDefinition

#### R18: Region write access enable register A
Region write access enable register A
This register defines which master agent function TAG identifier (TAG-ID) encodings are enabled or disabled for write accesses to the access protected region.
| RGNx_ACCEN_WRA (x=0-15) Size: 32 bits | Offset address: | 00080 H+x*20 H |
| --- | --- | --- |
| Region write access enable register A | Application Reset value: | 1000 0003 H |
| 31 | 30 | 29 | 28 | 27 | 26 | 25 | 24 | 23 | 22 | 21 | 20 | 19 | 18 | 17 | 16 |
| --- | --- | --- | --- | --- | --- | --- | --- | --- | --- | --- | --- | --- | --- | --- | --- |
| EN31 | EN30 | EN29 | EN28 | EN27 | EN26 | EN25 | EN24 | EN23 | EN22 | EN21 | EN20 | EN19 | EN18 | EN17 | EN16 |
| rh | rh | rh | rh | rh | rh | rh | rh | rh | rh | rh | rh | rh | rh | rh | rh |
| 15 | 14 | 13 | 12 | 11 | 10 | 9 | 8 | 7 | 6 | 5 | 4 | 3 | 2 | 1 | 0 |
| EN15 | EN14 | EN13 | EN12 | EN11 | EN10 | EN09 | EN08 | EN07 | EN06 | EN05 | EN04 | EN03 | EN02 | EN01 | EN00 |
| rh | rh | rh | rh | rh | rh | rh | rh | rh | rh | rh | rh | rh | rh | rh | rh |
| Field | Bits | Type | Description |
| --- | --- | --- | --- |
| ENq (q=00-31) | q | rh | Write access enable for Master TAG ID q This bit enables write access to the access protected region for transactions with the Master TAG ID q. 0 B Disabled for write access 1 B Enabled for write access |
- Object ID: id_AURIXTC4XX_B_IFX_ATVMC_CE_LMU_100_generic_Register_RGNx_ACCEN_WRA_10729
- Object type: RegisterDefinition

#### R19: Region write access enable register B
Region write access enable register B
This register defines which master agent function TAG identifier (TAG-ID) encodings are enabled or disabled for write accesses to the access protected region.
| RGNx_ACCEN_WRB (x=0-15) Size: 32 bits | Offset address: | 00084 H+x*20 H |
| --- | --- | --- |
| Region write access enable register B | Application Reset value: | 0000 0000 H |
| 31 | 30 | 29 | 28 | 27 | 26 | 25 | 24 | 23 | 22 | 21 | 20 | 19 | 18 | 17 | 16 |
| --- | --- | --- | --- | --- | --- | --- | --- | --- | --- | --- | --- | --- | --- | --- | --- |
| EN63 | EN62 | EN61 | EN60 | EN59 | EN58 | EN57 | EN56 | EN55 | EN54 | EN53 | EN52 | EN51 | EN50 | EN49 | EN48 |
| rh | rh | rh | rh | rh | rh | rh | rh | rh | rh | rh | rh | rh | rh | rh | rh |
| 15 | 14 | 13 | 12 | 11 | 10 | 9 | 8 | 7 | 6 | 5 | 4 | 3 | 2 | 1 | 0 |
| EN47 | EN46 | EN45 | EN44 | EN43 | EN42 | EN41 | EN40 | EN39 | EN38 | EN37 | EN36 | EN35 | EN34 | EN33 | EN32 |
| rh | rh | rh | rh | rh | rh | rh | rh | rh | rh | rh | rh | rh | rh | rh | rh |
| Field | Bits | Type | Description |
| --- | --- | --- | --- |
| ENq (q=32-63) | q-32 | rh | Write access enable for TAG-ID q This bit enables write access to the access protected region for transactions with the TAG-ID q. 0 B Disabled for write access 1 B Enabled for write access |
- Object ID: id_AURIXTC4XX_B_IFX_ATVMC_CE_LMU_100_generic_Register_RGNx_ACCEN_WRB_10734
- Object type: RegisterDefinition

#### R20: Region read access enable register A
Region read access enable register A
This register defines which master agent function TAG identifier (TAG-ID) encodings are enabled or disabled for read accesses to the access protected region.
| RGNx_ACCEN_RDA (x=0-15) Size: 32 bits | Offset address: | 00088 H+x*20 H |
| --- | --- | --- |
| Region read access enable register A | Application Reset value: | FFFF FFFF H |
| 31 | 30 | 29 | 28 | 27 | 26 | 25 | 24 | 23 | 22 | 21 | 20 | 19 | 18 | 17 | 16 |
| --- | --- | --- | --- | --- | --- | --- | --- | --- | --- | --- | --- | --- | --- | --- | --- |
| EN31 | EN30 | EN29 | EN28 | EN27 | EN26 | EN25 | EN24 | EN23 | EN22 | EN21 | EN20 | EN19 | EN18 | EN17 | EN16 |
| rh | rh | rh | rh | rh | rh | rh | rh | rh | rh | rh | rh | rh | rh | rh | rh |
| 15 | 14 | 13 | 12 | 11 | 10 | 9 | 8 | 7 | 6 | 5 | 4 | 3 | 2 | 1 | 0 |
| EN15 | EN14 | EN13 | EN12 | EN11 | EN10 | EN09 | EN08 | EN07 | EN06 | EN05 | EN04 | EN03 | EN02 | EN01 | EN00 |
| rh | rh | rh | rh | rh | rh | rh | rh | rh | rh | rh | rh | rh | rh | rh | rh |
| Field | Bits | Type | Description |
| --- | --- | --- | --- |
| ENq (q=00-31) | q | rh | Read access enable for TAG-ID q This bit enables read access to the access protected region for transactions with the TAG-ID q. 0 B Disabled for read access 1 B Enabled for read access |
- Object ID: id_AURIXTC4XX_B_IFX_ATVMC_CE_LMU_100_generic_Register_RGNx_ACCEN_RDA_10739
- Object type: RegisterDefinition

#### R21: Region read access enable register B
Region read access enable register B
This register defines which master agent function TAG identifier (TAG-ID) encodings are enabled or disabled for read accesses to the access protected region.
| RGNx_ACCEN_RDB (x=0-15) Size: 32 bits | Offset address: | 0008C H+x*20 H |
| --- | --- | --- |
| Region read access enable register B | Application Reset value: | FFFF FFFF H |
| 31 | 30 | 29 | 28 | 27 | 26 | 25 | 24 | 23 | 22 | 21 | 20 | 19 | 18 | 17 | 16 |
| --- | --- | --- | --- | --- | --- | --- | --- | --- | --- | --- | --- | --- | --- | --- | --- |
| EN63 | EN62 | EN61 | EN60 | EN59 | EN58 | EN57 | EN56 | EN55 | EN54 | EN53 | EN52 | EN51 | EN50 | EN49 | EN48 |
| rh | rh | rh | rh | rh | rh | rh | rh | rh | rh | rh | rh | rh | rh | rh | rh |
| 15 | 14 | 13 | 12 | 11 | 10 | 9 | 8 | 7 | 6 | 5 | 4 | 3 | 2 | 1 | 0 |
| EN47 | EN46 | EN45 | EN44 | EN43 | EN42 | EN41 | EN40 | EN39 | EN38 | EN37 | EN36 | EN35 | EN34 | EN33 | EN32 |
| rh | rh | rh | rh | rh | rh | rh | rh | rh | rh | rh | rh | rh | rh | rh | rh |
| Field | Bits | Type | Description |
| --- | --- | --- | --- |
| ENq (q=32-63) | q-32 | rh | Read access enable for TAG-ID q This bit enables read access to the access protected region for transactions with the TAG-ID q. 0 B Disabled for read access 1 B Enabled for read access |
- Object ID: id_AURIXTC4XX_B_IFX_ATVMC_CE_LMU_100_generic_Register_RGNx_ACCEN_RDB_10744
- Object type: RegisterDefinition

#### R22: Region VM access enable register
Region VM access enable register
This register defines which virtual machine encodings are enabled or disabled for accesses to the access protected region. There is one RDx and WRx bit for each VMx.
| RGNx_ACCEN_VM (x=0-15) Size: 32 bits | Offset address: | 00090 H+x*20 H |
| --- | --- | --- |
| Region VM access enable register | Application Reset value: | 00FF 00FF H |
| 31 | 30 | 29 | 28 | 27 | 26 | 25 | 24 | 23 | 22 | 21 | 20 | 19 | 18 | 17 | 16 |
| --- | --- | --- | --- | --- | --- | --- | --- | --- | --- | --- | --- | --- | --- | --- | --- |
| 0 |  |  |  |  |  |  |  | WR07 | WR06 | WR05 | WR04 | WR03 | WR02 | WR01 | WR00 |
| r |  |  |  |  |  |  |  | rh | rh | rh | rh | rh | rh | rh | rh |
| 15 | 14 | 13 | 12 | 11 | 10 | 9 | 8 | 7 | 6 | 5 | 4 | 3 | 2 | 1 | 0 |
| 0 |  |  |  |  |  |  |  | RD07 | RD06 | RD05 | RD04 | RD03 | RD02 | RD01 | RD00 |
| r |  |  |  |  |  |  |  | rh | rh | rh | rh | rh | rh | rh | rh |
| Field | Bits | Type | Description |
| --- | --- | --- | --- |
| RDq (q=00-07) | q | rh | Read access enable for VM ID q This bit enables read access to the access protected region for transactions with the VM ID q. 0 B Disabled for read access 1 B Enabled for read access |
| WRq (q=00-07) | q+16 | rh | Write access enable for VM ID q This bit enables write access to the access protected region for transactions with the VM ID q. 0 B Disabled for write access 1 B Enabled for write access |
| 0 | 15:8, 31:24 | r | Reserved Read as 0; should be written with 0. |
- Object ID: id_AURIXTC4XX_B_IFX_ATVMC_CE_LMU_100_generic_Register_RGNx_ACCEN_VM_10749
- Object type: RegisterDefinition

#### R23: Region PRS access enable register
Region PRS access enable register
This register defines which protection register set encodings are enabled or disabled for accesses to the access protected region. There is one RDx and WRx bit for each PRSx.
| RGNx_ACCEN_PRS (x=0-15) Size: 32 bits | Offset address: | 00094 H+x*20 H |
| --- | --- | --- |
| Region PRS access enable register | Application Reset value: | 00FF 00FF H |
| 31 | 30 | 29 | 28 | 27 | 26 | 25 | 24 | 23 | 22 | 21 | 20 | 19 | 18 | 17 | 16 |
| --- | --- | --- | --- | --- | --- | --- | --- | --- | --- | --- | --- | --- | --- | --- | --- |
| 0 |  |  |  |  |  |  |  | WR07 | WR06 | WR05 | WR04 | WR03 | WR02 | WR01 | WR00 |
| r |  |  |  |  |  |  |  | rh | rh | rh | rh | rh | rh | rh | rh |
| 15 | 14 | 13 | 12 | 11 | 10 | 9 | 8 | 7 | 6 | 5 | 4 | 3 | 2 | 1 | 0 |
| 0 |  |  |  |  |  |  |  | RD07 | RD06 | RD05 | RD04 | RD03 | RD02 | RD01 | RD00 |
| r |  |  |  |  |  |  |  | rh | rh | rh | rh | rh | rh | rh | rh |
| Field | Bits | Type | Description |
| --- | --- | --- | --- |
| RDq (q=00-07) | q | rh | Read access enable for PRS q This bit enables read access to the access protected region for transactions with the PRS q. 0 B Disabled for read access 1 B Enabled for read access |
| WRq (q=00-07) | q+16 | rh | Write access enable for PRS q This bit enables write access to the access protected region for transactions with the PRS q. 0 B Disabled for write access 1 B Enabled for write access |
| 0 | 15:8, 31:24 | r | Reserved Read as 0; should be written with 0. |
- Object ID: id_AURIXTC4XX_B_IFX_ATVMC_CE_LMU_100_generic_Register_RGNx_ACCEN_PRS_10754
- Object type: RegisterDefinition

#### R24: Region lower address register
Region lower address register
This register sets the lower bound of the access protected region. Addresses greater than or equal to the lower bound are considered part of the access protected region.
| RGNx_ACCEN_RGNLA (x=0-15) Size: 32 bits | Offset address: | 00098 H+x*20 H |
| --- | --- | --- |
| Region lower address register | Application Reset value: | 0000 0000 H |
| 31 | 30 | 29 | 28 | 27 | 26 | 25 | 24 | 23 | 22 | 21 | 20 | 19 | 18 | 17 | 16 |
| --- | --- | --- | --- | --- | --- | --- | --- | --- | --- | --- | --- | --- | --- | --- | --- |
| ADDRH |  | 0 | ADDR |  |  |  |  |  |  |  |  |  |  |  |  |
| rh |  | r | rh |  |  |  |  |  |  |  |  |  |  |  |  |
| 15 | 14 | 13 | 12 | 11 | 10 | 9 | 8 | 7 | 6 | 5 | 4 | 3 | 2 | 1 | 0 |
| ADDR |  |  |  |  |  |  |  |  |  | 0 |  |  |  |  |  |
| rh |  |  |  |  |  |  |  |  |  | r |  |  |  |  |  |
| Field | Bits | Type | Description |
| --- | --- | --- | --- |
| ADDR | 28:6 | rh | Defines bits 28:6 of the lower bound of the access protected region |
| ADDRH | 31:30 | rh | Defines bits 31:30 of the lower bound of the access protected region |
| 0 | 5:0, 29 | r | Reserved Read as 0; should be written with 0. |
- Object ID: id_AURIXTC4XX_B_IFX_ATVMC_CE_LMU_100_generic_Register_RGNx_ACCEN_RGNLA_10790
- Object type: RegisterDefinition

#### R25: Region upper address register
Region upper address register
This register sets the upper bound of the access protected region. Addresses stricly less than the upper bound are considered part of the access protected region.
| RGNx_ACCEN_RGNUA (x=0-15) Size: 32 bits | Offset address: | 0009C H+x*20 H |
| --- | --- | --- |
| Region upper address register | Application Reset value: | DFFF FFC0 H |
| 31 | 30 | 29 | 28 | 27 | 26 | 25 | 24 | 23 | 22 | 21 | 20 | 19 | 18 | 17 | 16 |
| --- | --- | --- | --- | --- | --- | --- | --- | --- | --- | --- | --- | --- | --- | --- | --- |
| ADDRH |  | 0 | ADDR |  |  |  |  |  |  |  |  |  |  |  |  |
| rh |  | r | rh |  |  |  |  |  |  |  |  |  |  |  |  |
| 15 | 14 | 13 | 12 | 11 | 10 | 9 | 8 | 7 | 6 | 5 | 4 | 3 | 2 | 1 | 0 |
| ADDR |  |  |  |  |  |  |  |  |  | 0 |  |  |  |  |  |
| rh |  |  |  |  |  |  |  |  |  | r |  |  |  |  |  |
| Field | Bits | Type | Description |
| --- | --- | --- | --- |
| ADDR | 28:6 | rh | Defines bits 28:6 of the upper bound of the access protected region |
| ADDRH | 31:30 | rh | Defines bits 31:30 of the upper bound of the access protected region |
| 0 | 5:0, 29 | r | Reserved Read as 0; should be written with 0. |
- Object ID: id_AURIXTC4XX_B_IFX_ATVMC_CE_LMU_100_generic_Register_RGNx_ACCEN_RGNUA_10795
- Object type: RegisterDefinition

#### R26
Configure region write access enable register A
The shadow region access enable registers allow atomic update of one region configuration under the control of the PROTRGN state machine. The value of the PROTRGN.SEL register bit-field determines which APU is configured.
This register defines which master agent function TAG identifier (TAG-ID) encodings are enabled or disabled for write accesses to the access protected region.
| ACCENCFG_WRA Size: 32 bits | Offset address: | 00300 H |
| --- | --- | --- |
| Configure region write access enable register A | Application Reset value: | 1000 0003 H |
| 31 | 30 | 29 | 28 | 27 | 26 | 25 | 24 | 23 | 22 | 21 | 20 | 19 | 18 | 17 | 16 |
| --- | --- | --- | --- | --- | --- | --- | --- | --- | --- | --- | --- | --- | --- | --- | --- |
| EN31 | EN30 | EN29 | EN28 | EN27 | EN26 | EN25 | EN24 | EN23 | EN22 | EN21 | EN20 | EN19 | EN18 | EN17 | EN16 |
| rw | rw | rw | rw | rw | rw | rw | rw | rw | rw | rw | rw | rw | rw | rw | rw |
| 15 | 14 | 13 | 12 | 11 | 10 | 9 | 8 | 7 | 6 | 5 | 4 | 3 | 2 | 1 | 0 |
| EN15 | EN14 | EN13 | EN12 | EN11 | EN10 | EN09 | EN08 | EN07 | EN06 | EN05 | EN04 | EN03 | EN02 | EN01 | EN00 |
| rw | rw | rw | rw | rw | rw | rw | rw | rw | rw | rw | rw | rw | rw | rw | rw |
| Field | Bits | Type | Description |
| --- | --- | --- | --- |
| ENq (q=00-31) | q | rw | Write access enable for TAG-ID q This bit enables write access to the access protected region for transactions with the TAG-ID q. 0 B Disabled for write access 1 B Enabled for write access |
- Object ID: id_AURIXTC4XX_B_IFX_ATVMC_CE_LMU_100_generic_Register_ACCENCFG_WRA_10760
- Object type: RegisterDefinition

#### R27
Configure region write access enable register B
The shadow region access enable registers allow atomic update of one region configuration under the control of the PROTRGN state machine. The value of the PROTRGN.SEL register bit-field determines which APU is configured.
This register defines which master agent function TAG identifier (TAG-ID) encodings are enabled or disabled for write accesses to the access protected region.
| ACCENCFG_WRB Size: 32 bits | Offset address: | 00304 H |
| --- | --- | --- |
| Configure region write access enable register B | Application Reset value: | 0000 0000 H |
| 31 | 30 | 29 | 28 | 27 | 26 | 25 | 24 | 23 | 22 | 21 | 20 | 19 | 18 | 17 | 16 |
| --- | --- | --- | --- | --- | --- | --- | --- | --- | --- | --- | --- | --- | --- | --- | --- |
| EN63 | EN62 | EN61 | EN60 | EN59 | EN58 | EN57 | EN56 | EN55 | EN54 | EN53 | EN52 | EN51 | EN50 | EN49 | EN48 |
| rw | rw | rw | rw | rw | rw | rw | rw | rw | rw | rw | rw | rw | rw | rw | rw |
| 15 | 14 | 13 | 12 | 11 | 10 | 9 | 8 | 7 | 6 | 5 | 4 | 3 | 2 | 1 | 0 |
| EN47 | EN46 | EN45 | EN44 | EN43 | EN42 | EN41 | EN40 | EN39 | EN38 | EN37 | EN36 | EN35 | EN34 | EN33 | EN32 |
| rw | rw | rw | rw | rw | rw | rw | rw | rw | rw | rw | rw | rw | rw | rw | rw |
| Field | Bits | Type | Description |
| --- | --- | --- | --- |
| ENq (q=32-63) | q-32 | rw | Write access enable for TAG-ID q This bit enables write access to the access protected region for transactions with the TAG-ID q. 0 B Disabled for write access 1 B Enabled for write access |
- Object ID: id_AURIXTC4XX_B_IFX_ATVMC_CE_LMU_100_generic_Register_ACCENCFG_WRB_10765
- Object type: RegisterDefinition

#### R28
Configure region read access enable register A
The shadow region access enable registers allow atomic update of one region configuration under the control of the PROTRGN state machine. The value of the PROTRGN.SEL register bit-field determines which APU is configured.
This register defines which master agent function TAG identifier (TAG-ID) encodings are enabled or disabled for read accesses to the access protected region.
| ACCENCFG_RDA Size: 32 bits | Offset address: | 00308 H |
| --- | --- | --- |
| Configure region read access enable register A | Application Reset value: | FFFF FFFF H |
| 31 | 30 | 29 | 28 | 27 | 26 | 25 | 24 | 23 | 22 | 21 | 20 | 19 | 18 | 17 | 16 |
| --- | --- | --- | --- | --- | --- | --- | --- | --- | --- | --- | --- | --- | --- | --- | --- |
| EN31 | EN30 | EN29 | EN28 | EN27 | EN26 | EN25 | EN24 | EN23 | EN22 | EN21 | EN20 | EN19 | EN18 | EN17 | EN16 |
| rw | rw | rw | rw | rw | rw | rw | rw | rw | rw | rw | rw | rw | rw | rw | rw |
| 15 | 14 | 13 | 12 | 11 | 10 | 9 | 8 | 7 | 6 | 5 | 4 | 3 | 2 | 1 | 0 |
| EN15 | EN14 | EN13 | EN12 | EN11 | EN10 | EN09 | EN08 | EN07 | EN06 | EN05 | EN04 | EN03 | EN02 | EN01 | EN00 |
| rw | rw | rw | rw | rw | rw | rw | rw | rw | rw | rw | rw | rw | rw | rw | rw |
| Field | Bits | Type | Description |
| --- | --- | --- | --- |
| ENq (q=00-31) | q | rw | Read access enable for TAG-ID q This bit enables read access to the access protected region for transactions with the TAG-ID q. 0 B Disabled for read access 1 B Enabled for read access |
- Object ID: id_AURIXTC4XX_B_IFX_ATVMC_CE_LMU_100_generic_Register_ACCENCFG_RDA_10770
- Object type: RegisterDefinition

#### R29
Configure region read access enable register B
The shadow region access enable registers allow atomic update of one region configuration under the control of the PROTRGN state machine. The value of the PROTRGN.SEL register bit-field determines which APU is configured.
This register defines which master agent function TAG identifier (TAG-ID) encodings are enabled or disabled for read accesses to the access protected region.
| ACCENCFG_RDB Size: 32 bits | Offset address: | 0030C H |
| --- | --- | --- |
| Configure region read access enable register B | Application Reset value: | FFFF FFFF H |
| 31 | 30 | 29 | 28 | 27 | 26 | 25 | 24 | 23 | 22 | 21 | 20 | 19 | 18 | 17 | 16 |
| --- | --- | --- | --- | --- | --- | --- | --- | --- | --- | --- | --- | --- | --- | --- | --- |
| EN63 | EN62 | EN61 | EN60 | EN59 | EN58 | EN57 | EN56 | EN55 | EN54 | EN53 | EN52 | EN51 | EN50 | EN49 | EN48 |
| rw | rw | rw | rw | rw | rw | rw | rw | rw | rw | rw | rw | rw | rw | rw | rw |
| 15 | 14 | 13 | 12 | 11 | 10 | 9 | 8 | 7 | 6 | 5 | 4 | 3 | 2 | 1 | 0 |
| EN47 | EN46 | EN45 | EN44 | EN43 | EN42 | EN41 | EN40 | EN39 | EN38 | EN37 | EN36 | EN35 | EN34 | EN33 | EN32 |
| rw | rw | rw | rw | rw | rw | rw | rw | rw | rw | rw | rw | rw | rw | rw | rw |
| Field | Bits | Type | Description |
| --- | --- | --- | --- |
| ENq (q=32-63) | q-32 | rw | Read access enable for TAG-ID q This bit enables read access to the access protected region for transactions with the TAG-ID q. 0 B Disabled for read access 1 B Enabled for read access |
- Object ID: id_AURIXTC4XX_B_IFX_ATVMC_CE_LMU_100_generic_Register_ACCENCFG_RDB_10775
- Object type: RegisterDefinition

#### R30
Configure region VM access enable register
The shadow region access enable registers allow atomic update of one region configuration under the control of the PROTRGN state machine. The value of the PROTRGN.SEL register bit-field determines which APU is configured.
This register defines which virtual machine encodings are enabled or disabled for accesses to the access protected region. There is one RDx and WRx bit for each VMx.
| ACCENCFG_VM Size: 32 bits | Offset address: | 00310 H |
| --- | --- | --- |
| Configure region VM access enable register | Application Reset value: | 00FF 00FF H |
| 31 | 30 | 29 | 28 | 27 | 26 | 25 | 24 | 23 | 22 | 21 | 20 | 19 | 18 | 17 | 16 |
| --- | --- | --- | --- | --- | --- | --- | --- | --- | --- | --- | --- | --- | --- | --- | --- |
| 0 |  |  |  |  |  |  |  | WR07 | WR06 | WR05 | WR04 | WR03 | WR02 | WR01 | WR00 |
| r |  |  |  |  |  |  |  | rw | rw | rw | rw | rw | rw | rw | rw |
| 15 | 14 | 13 | 12 | 11 | 10 | 9 | 8 | 7 | 6 | 5 | 4 | 3 | 2 | 1 | 0 |
| 0 |  |  |  |  |  |  |  | RD07 | RD06 | RD05 | RD04 | RD03 | RD02 | RD01 | RD00 |
| r |  |  |  |  |  |  |  | rw | rw | rw | rw | rw | rw | rw | rw |
| Field | Bits | Type | Description |
| --- | --- | --- | --- |
| RDq (q=00-07) | q | rw | Read access enable for VM ID q This bit enables read access to the access protected region for transactions with the VM ID q. 0 B Disabled for read access 1 B Enabled for read access |
| WRq (q=00-07) | q+16 | rw | Write access enable for VM ID q This bit enables write access to the access protected region for transactions with the VM ID q. 0 B Disabled for write access 1 B Enabled for write access |
| 0 | 15:8, 31:24 | r | Reserved Read as 0; should be written with 0. |
- Object ID: id_AURIXTC4XX_B_IFX_ATVMC_CE_LMU_100_generic_Register_ACCENCFG_VM_10780
- Object type: RegisterDefinition

#### R31
Configure region PRS access enable register
The shadow region access enable registers allow atomic update of one region configuration under the control of the PROTRGN state machine. The value of the PROTRGN.SEL register bit-field determines which APU is configured.
This register defines which protection register set encodings are enabled or disabled for accesses to the access protected region. There is one RDx and WRx bit for each PRSx.
| ACCENCFG_PRS Size: 32 bits | Offset address: | 00314 H |
| --- | --- | --- |
| Configure region PRS access enable register | Application Reset value: | 00FF 00FF H |
| 31 | 30 | 29 | 28 | 27 | 26 | 25 | 24 | 23 | 22 | 21 | 20 | 19 | 18 | 17 | 16 |
| --- | --- | --- | --- | --- | --- | --- | --- | --- | --- | --- | --- | --- | --- | --- | --- |
| 0 |  |  |  |  |  |  |  | WR07 | WR06 | WR05 | WR04 | WR03 | WR02 | WR01 | WR00 |
| r |  |  |  |  |  |  |  | rw | rw | rw | rw | rw | rw | rw | rw |
| 15 | 14 | 13 | 12 | 11 | 10 | 9 | 8 | 7 | 6 | 5 | 4 | 3 | 2 | 1 | 0 |
| 0 |  |  |  |  |  |  |  | RD07 | RD06 | RD05 | RD04 | RD03 | RD02 | RD01 | RD00 |
| r |  |  |  |  |  |  |  | rw | rw | rw | rw | rw | rw | rw | rw |
| Field | Bits | Type | Description |
| --- | --- | --- | --- |
| RDq (q=00-07) | q | rw | Read access enable for PRS q This bit enables read access to the access protected region for transactions with the PRS q. 0 B Disabled for read access 1 B Enabled for read access |
| WRq (q=00-07) | q+16 | rw | Write access enable for PRS q This bit enables write access to the access protected region for transactions with the PRS q. 0 B Disabled for write access 1 B Enabled for write access |
| 0 | 15:8, 31:24 | r | Reserved Read as 0; should be written with 0. |
- Object ID: id_AURIXTC4XX_B_IFX_ATVMC_CE_LMU_100_generic_Register_ACCENCFG_PRS_10785
- Object type: RegisterDefinition

#### R32: Configure region lower address register
Configure region lower address register
The shadow region access enable registers allow atomic update of one region configuration under the control of the PROTRGN state machine. The value of the PROTRGN.SEL register bit-field determines which APU is configured.
This register sets the lower bound of the access protected region. Addresses greater than or equal to the lower bound are considered part of the access protected region.
| ACCENCFG_RGNLA Size: 32 bits | Offset address: | 00318 H |
| --- | --- | --- |
| Configure region lower address register | Application Reset value: | 0000 0000 H |
| 31 | 30 | 29 | 28 | 27 | 26 | 25 | 24 | 23 | 22 | 21 | 20 | 19 | 18 | 17 | 16 |
| --- | --- | --- | --- | --- | --- | --- | --- | --- | --- | --- | --- | --- | --- | --- | --- |
| ADDRH |  | 0 | ADDR |  |  |  |  |  |  |  |  |  |  |  |  |
| rw |  | r | rw |  |  |  |  |  |  |  |  |  |  |  |  |
| 15 | 14 | 13 | 12 | 11 | 10 | 9 | 8 | 7 | 6 | 5 | 4 | 3 | 2 | 1 | 0 |
| ADDR |  |  |  |  |  |  |  |  |  | 0 |  |  |  |  |  |
| rw |  |  |  |  |  |  |  |  |  | r |  |  |  |  |  |
| Field | Bits | Type | Description |
| --- | --- | --- | --- |
| ADDR | 28:6 | rw | Defines bits 28:6 of the lower bound of the access protected region |
| ADDRH | 31:30 | rw | Defines bits 31:30 of the lower bound of the access protected region |
| 0 | 5:0, 29 | r | Reserved Read as 0; should be written with 0. |
- Object ID: id_AURIXTC4XX_B_IFX_ATVMC_CE_LMU_100_generic_Register_ACCENCFG_RGNLA_10801
- Object type: RegisterDefinition

#### R33: Configure region upper address register
Configure region upper address register
The shadow region access enable registers allow atomic update of one region configuration under the control of the PROTRGN state machine. The value of the PROTRGN.SEL register bit-field determines which APU is configured.
This register sets the upper bound of the access protected region. Addresses stricly less than the upper bound are considered part of the access protected region.
| ACCENCFG_RGNUA Size: 32 bits | Offset address: | 0031C H |
| --- | --- | --- |
| Configure region upper address register | Application Reset value: | DFFF FFC0 H |
| 31 | 30 | 29 | 28 | 27 | 26 | 25 | 24 | 23 | 22 | 21 | 20 | 19 | 18 | 17 | 16 |
| --- | --- | --- | --- | --- | --- | --- | --- | --- | --- | --- | --- | --- | --- | --- | --- |
| ADDRH |  | 0 | ADDR |  |  |  |  |  |  |  |  |  |  |  |  |
| rw |  | r | rw |  |  |  |  |  |  |  |  |  |  |  |  |
| 15 | 14 | 13 | 12 | 11 | 10 | 9 | 8 | 7 | 6 | 5 | 4 | 3 | 2 | 1 | 0 |
| ADDR |  |  |  |  |  |  |  |  |  | 0 |  |  |  |  |  |
| rw |  |  |  |  |  |  |  |  |  | r |  |  |  |  |  |
| Field | Bits | Type | Description |
| --- | --- | --- | --- |
| ADDR | 28:6 | rw | Defines bits 28:6 of the upper bound of the access protected region |
| ADDRH | 31:30 | rw | Defines bits 31:30 of the upper bound of the access protected region |
| 0 | 5:0, 29 | r | Reserved Read as 0; should be written with 0. |
- Object ID: id_AURIXTC4XX_B_IFX_ATVMC_CE_LMU_100_generic_Register_ACCENCFG_RGNUA_10804
- Object type: RegisterDefinition

### R34: Debug information
- Object ID: LYBA-EFCI-GCGE-IGHH
- Object type: Information

### R35: References
- Object ID: QNVA-EDJE-GFCB-BBEG
- Object type: Information

### R36: LMU revision history
- Object ID: ICZA-EDJE-GFCB-CJAJ
- Object type: Information

### d1116e373: TC4Dx LMU information
- Object type: Information

#### R38: TC4Dx LMU configuration
- Object ID: NZZA-FJGA-JJCC-IIGC
- Object type: Information

#### R39: TC4Dx LMU features
TC4Dx LMU features
The TC4D device has ten instances of the LMU of which six are capable of being powered off. The instances named: LMU4, LMU5, LMU6, LMU7, LMU8, and LMU9 can be powered down. The power is controlled and monitored for two groups of instances powered by the domains named as indicated:
- LMU4, LMU5 and LMU6: VDDLMU0
- LMU7, LMU8, and LMU9: VDDLMU1
- Object ID: GGQA-FJGA-JJCD-BIGH
- Object type: Information

#### R40: TC4Dx LMU functional description
- Object ID: MYKA-FJGA-JJCD-CGIH
- Object type: Information

#### R41: TC4Dx LMU registers
- Object ID: UDGA-FJGA-JJCD-AEHI
- Object type: Information

#### d2: TC4DX LMU connectivity
TC4DX LMU connectivity
List of LMU interface signals
| Interface signals | I/O | Description |
| --- | --- | --- |
| LMU_SMU_ALARMx | Out | LMUx alarm |
The table below lists all interfaces of the LMU to other modules in the device.
- Object type: Information

#### R43: TC4Dx LMU revision history
- Object ID: ZIEA-FJGA-JJCD-BCHF
- Object type: Information
