# AURIX TC43x Safety Manual

# Specification: Specification Document
- Description: AURIX TC43x Safety Manual

## METADATA: Metadata
| id | value |
| --- | --- |
| title | AURIX™ TC43x Safety Manual |
| subtitle |  |
| doc_type | Safety Manual |
| doc_version | V0.4 |
- ReqIF-WF.Type: Information

## DISCLAIMER: Disclaimer
Infineon provides the ReqIFz file as an optional supporting delivery to the officially released PDF documentation.
The content of the ReqIF file reflects the structure and content of the corresponding PDF document.
The ReqIF file is validated against the ReqIF standard.
The ReqIF file is not qualified according to ISO 26262, therefore Infineon Technologies AG disclaims any liability in connection with the use of this information.
- ReqIF-WF.Type: Information

## JDNA-EIAB-GGCJ-DDGJ: About this document
| Name | Package | Marking |
| --- | --- | --- |
| AURIX™ TC43x | All packages | All markings |
- IFX.Version: 18
- ReqIF-WF.Type: Information

### JDNA-EIAB-GGCJ-DDGJ-002
Scope and purpose
The product(s) described in this safety manual has been developed and is released as ISO 26262:2018 safety element out of context for safety requirements up to Automotive safety integrity level D.
If the product is intended to be used in a functional safety application, you are obliged to ensure conformity with the relevant requirements of ISO 26262:2018.
In particular you are obliged to obtain the available product safety documents and to respect the information and information updates provided by Infineon Technologies.
In the event that you merely resell the product as a distributor, you are obliged to ensure that your customers obtain the available product safety documents and that your customers respect the information and information updates provided by Infineon Technologies.
Information updates are provided through Product Change Notification (PCN), Info Note or Early Problem Notification (EPN) or any other written communication to customers or distributors that have ordered the product within the last 5 years. The complete updated safety document is available at the Infineon sales office.
The table below lists the products covered by this document.
- ReqIF-WF.Type: Requirement

## NSLA-EIGH-BEDB-FGGI: Introduction
Please read this manual carefully and be sure you understand the information provided before integrating the device in a safety-related application.
- IFX.Version: 6
- ReqIF-WF.Type: Information

### SXWA-EIAB-HACJ-FBBC: Document overview
A description of the function of the device is provided in the user manual. Device overview summarizes the safety properties of the device and provides an overview of the internal safety mechanisms and the specification of the external safety mechanisms. It further describes the detected and indicated faults and how they can be handled in the application.
The assumed application use cases and application level environment are described in TLSR use cases. In this chapter each individual use case is explained. The reader will also find a table with the assumptions of use for hardware or software implementation that apply specifically to the corresponding use case. Also a table with the required safety mechanisms is provided. With this information the system integrator will know which safety mechanisms need to be implemented to realize a particular use case. Furthermore, the mentioned assumptions of use and safety mechanisms were the basis for the safety analysis.
- IFX.Version: 9
- ReqIF-WF.Type: Information

### LJSA-FDFC-BJDB-ABFA: Intended audience
This safety manual is written for experienced hardware, software and functional safety engineers involved in the design or development of a safety-related system according to ISO 26262 which consider to integrate the AURIX™ TC43x microcontroller into their (sub-) system. It is the responsibility of the integrator to ensure that the product is suitable for the chosen application and complies with the applicable application standards.
- IFX.Version: 2
- ReqIF-WF.Type: Information

### YGFA-FDFC-BJHI-GBAD: Functional safety
The achievement of a specific ASIL rating at the application level for a specific safety requirement is the system integrator’s responsibility. Any deviations from the instructions given in this document shall be justified with a rationale and are the sole responsibility of the system integrator.
- IFX.Version: 3
- ReqIF-WF.Type: Information

### XJPA-FDFC-BBBE-JCEE: Scope for the system integrator
The safety measures and the assumptions of use shown in this document have been verified for the described application use cases under the operating conditions and mission profiles specified for this device. It is the responsibility of the system integrator to verify that the device, its configuration in the application, mission profile, the safety requirements, safety measures and assumptions of use given in this document are suitable for the chosen application, considering also the tolerances and boundary conditions of the application.
Compliance with applicable standards on system level is in the system integrator’s responsibility as well.
The safety analysis results (provided separately) are valid for the described application conditions in the use cases shown in TLSR use cases. If certain assumptions of use are not implemented by the system integrator, an equivalent measure or argumentation that the assumption is not applicable for the considered system must be implemented or provided. The impact on the safety analysis results must be assessed.
Please consult Infineon if you have any questions or comments relating to the information provided in this document.
Note: The mission profile and operating conditions are provided in the device specific FMEDA sheet and in the Safety analysis summary report (SASR). These documents are provided separately. See also the References chapter.
- IFX.Version: 3
- ReqIF-WF.Type: Information

### HGQA-EIGH-CHEA-JJED: Infineon PRO-SIL™ ISO 26262-compliant
Infineon PRO-SIL™ ISO 26262-compliant safety products fulfill the properties required by the ISO 26262 (Automotive Safety) standard. PRO-SIL™ ISO 26262-compliant product development follows a product specific safety plan defined by Infineon. The product development follows the Infineon V–model based development lifecycle which encompasses all ISO 26262 required activities and work products related to the product scope.
An independent functional safety management organization supports the ISO 26262 conform safety lifecycle.
- IFX.Version: 5
- ReqIF-WF.Type: Information

### TFJA-EIAB-HAFG-CJIJ: Required additional reading
This document is limited to those technical actions that are required to ensure compliance with the relevant safety standards. Other documents such as the datasheet must be referred to for information outside the scope of this document. A list of the relevant documents can be found in References.
- IFX.Version: 8
- ReqIF-WF.Type: Information

### GSPA-FDFG-BJIH-ADDD: Terms and definitions
This chapter introduces the terms and definitions that are used throughout this document.
- IFX.Version: 2
- ReqIF-WF.Type: Information

#### PPNA-EIAG-JDJC-JFJF: Glossary terms
In this manual the words in italic (for example microcontroller unit) are defined in the Glossary. In order to avoid any kind of confusion, please refer to the definition provided in this manual only.
- IFX.Version: 9
- ReqIF-WF.Type: Information

#### QIQA-EIAG-JDJG-HCGD: Safety mechanism identifiers
A safety mechanism is defined as an activity or a technical solution to control systematic failures and to detect or control random hardware failures. While systematic failures can only be mitigated during the design phase, random hardware failures can be detected during the operation by one or several safety measures, which are classified in two main types:
- safety mechanism: technical solution internal to the microcontroller unit by hardware or software.
- external safety mechanism: technical solution either in HW or SW, implemented at system level by the system integrator.
These two categories are used to mitigate single points and residual faults for single-point fault metric and to avoid dual-point faults from being latent for latent fault metric.
To distinguish these categories, the following conventions are used in this document:
- SM[HW]:FB:DESCRIPTION
SM[HW] refers to a safety mechanism that is implemented by the microcontroller unit hardware. functional block refers to the Functional Block of the microcontroller unit that performs the monitoring function. The DESCRIPTION field gives a short information about the mechanism.
- SM[SW]:FB:DESCRIPTION
SM[SW] refers to a safety mechanism implemented by software provided by Infineon in addition of the microcontroller unit hardware product. functional block refers to the Functional Block of the microcontroller unit that is monitored by the safety mechanism. The DESCRIPTION field gives a short information about the mechanism.
- ESM[HW]:FB:DESCRIPTION
ESM[HW] refers to an external safety mechanism to be implemented by the application hardware. functional block refers to the Functional Block of the microcontroller unit that relies on the external mechanism. The DESCRIPTION field gives a short information about the mechanism.
- ESM[SW]:FB:DESCRIPTION
ESM[SW] refers to an external safety mechanism to be implemented by Application SW. functional block refers to the Functional Block of the microcontroller unit that relies on the external mechanism. The DESCRIPTION field gives a short information about the mechanism.
- IFX.Version: 7
- ReqIF-WF.Type: Information

#### ZSQA-EIAG-JDAB-JICC: Description of hardware safety mechanisms
Hardware safety mechanism, either internal or external, are located under each functional block in Safety Mechanisms. The text describing every safety mechanism is organized in different sections as shown below:
Identifier
This is the name given to the (E)SM[HW]. Each safety mechanism has a unique identifier which follows the structure shown in the section Safety mechanism identifiers.
Description
Gives an overview of the monitoring function performed by the (E)SM[HW].
Reset operational state
This field specified which type of reset affects the safety mechanism and how.
Configuration and activation
This specifies the actions that application software shall undertake to configure and activate this safety mechanism. For some safety mechanisms, also application software actions required during run-time are described here.
Test
To comply with the latent fault metric requirements of ISO 26262, a method to test safety mechanisms (which cover single point faults) is provided in this field. If no hardware measure is available for the test, this field will provide a method to test if by software. If the standard LBIST monitor is available for that, 'N.A.' will appear.
Reporting
This field will explain which events/errors will be notified by the safety mechanism and how.
Recommended error reaction
This field will provide a recommendation on how to handle errors reported by the safety mechanism if there is any.
Alarms table
After the 'Internal safety mechanisms' chapter a table is shown. This table provides an overview of all the alarms available for a particular functional block and the internal safety mechanisms associated with them. Please not that only internal hardware safety mechanisms feature alarms to the safety and security alarm management unit.
- IFX.Version: 9
- ReqIF-WF.Type: Information

#### JLFA-EIAG-JDAG-HDIE: Description of software safety mechanisms
Software safety mechanism, either internal or external, are located under each functional block in Safety Mechanisms. The text describing every safety mechanism is organized in different sections as shown below:
Identifier
This is the name given to the (E)SM[SW]. Each safety mechanism has a unique identifier which follows the structure shown in the section Safety mechanism identifiers.
Description
This section provides a description of the action or actions that the system integrator shall undertake at SW level in order to implement the (E)SM[SW] properly. In this field the user will find instructions in order to configure the microcontroller unit and/or correctly monitor or react to a fault during run-time, in case an safety and security alarm management unit alarm is not provided by HW.
- IFX.Version: 6
- ReqIF-WF.Type: Information

#### XKDA-FJGJ-JAAB-DFAH: Integration requirements
Integration requirements are provided in form of tables for each use case described in TLSR use cases. These tables will guide the system integrator in knowing which assumptions of use and safety mechanisms are required to successfully implement a particular use case. Each table contains 3 colums as shown in the example below.
Example of a requirements
table
| Type | Description | Comment |
| --- | --- | --- |
| This column specifies the type of requirement: - assumptions of use - Integration requirement | This column describes the assumptions of use or the requirement itself | In this column additional information may be added |
Note: even though the SM[HW] are already implemented in the microcontroller unit, some of them require additional actions performed by the application software. This information is shown in the field "Configuration and activation" as shown in Description of hardware safety mechanisms
- IFX.Version: 5
- ReqIF-WF.Type: Information

#### UXEA-FDFG-BACA-JHFF: Mission and monitoring channel
The terms 'mission channel' and 'monitoring channel' are used multiple times in this document. The following paragraphs will provide their definition.
Mission channel
In the context of an ASIL function, the mission channel carries the data or signals that are used by the application to fulfill its main task. For example, this could be the value measured by an analog to digital converter or a digital signal attached to a general purpose input. A fault in the mission channel that can lead to a violation of the safety goal is classified, according to the definitions of the ISO 26262, as a single point fault (SPF).
Monitoring channel
One method to detect faults in the mission channel is to implement a second channel that carries data or a signal that is correlated to the data or signal being carried by the mission channel. This is the so called 'monitoring channel' and it exists only for the purpose of detecting faults in the mission channel. The data or the signal carried by this channel is usually not used to feed the application main task but to ensure safety by means of comparison, plausibility checks, or other similar methods. The data or signal carried by the monitoring channel might be identical to the mission channel which could be the case for redundancy scenarios while in other cases it could be of lower resolution, sample rate, etc. just to enable the detection of faults in the mission channel according to the ASIL requirements of the safety related function.
- IFX.Version: 3
- ReqIF-WF.Type: Information

## LFXA-EIAB-GGCJ-FDIF: Device overview
- IFX.Version: 4
- ReqIF-WF.Type: Information

### ODDA-EIAB-HBAI-BAGA: Functional description
Please refer to the AURIX™ TC43x user manual for a detailed description of the product's features and functionalities.
- IFX.Version: 5
- ReqIF-WF.Type: Information

### NLUA-FCBI-ICJA-AIIE: Top level safety requirements
This section provides the safety requirements which were input to the development process, which are fulfilled by the AURIX™ TC43x microcontroller. The AURIX™ TC43x Microcontroller fulfills these requirements for the use cases provided in the chapter TLSR use cases if the assumptions of use (AoU) and integration requirements are followed by the system integrator.
MCU Safety Related Functions
TLSRs
| TLSR No. | TLSR Name | TLSR ASIL |
| --- | --- | --- |
| 1 | Safe software execution platform | ASIL D |
| 2 | Safe EEPROM access | ASIL B |
| 3 | Safe MCU infrastructure | ASIL D |
| 4 | Safe co-processing | ASIL B |
| 5 | Safe MCU boot | ASIL D |
| 6 | Safe digital acquisition | ASIL D |
| 7 | Safe analog acquisition | ASIL D |
| 8 | Safe single input analog acquisition | ASIL B |
| 9 | Safe digital actuation | ASIL D |
| 10 | Safe MCU external communication | ASIL D |
| 11 | Safe radar processing | ASIL B |
| 12 | Safe security management | ASIL D |
| 13 | Systematic fault avoidance of MCU | ASIL D |
Safe State Support TLSRs
| TLSR No. | TLSR Name | TLSR ASIL |
| --- | --- | --- |
| 14 | Internal failure reporting | ASIL D |
| 15 | External failure reporting | ASIL D |
| 16 | Alternate external failure reporting | ASIL D |
Dependent Failures TLSRs
| TLSR No. | TLSR Name | TLSR ASIL |
| --- | --- | --- |
| 17 | Avoidance or detection of common cause failure | ASIL D |
| 18 | Coexistence of hardware elements | ASIL D |
| 19 | Coexistence of software elements | ASIL D |
As basis for the safety analysis, a required maximum product safety time or fault detection and reaction time is specified per safety requirement. The safety time or fault detection and reaction time is defined as the time between the fault occurring in the product and the fault indication becoming visible on the IC device interface. This time has to be considered for the system Fault Tolerant Time Interval (FTTI) calculations according to ISO 26262-1:2018 3.61.
Please refer to the chapter below for more details.
- IFX.Version: 5
- ReqIF-WF.Type: Information

#### BYOA-FCBI-BDCG-BBIB: Safety mechanisms DTTI
The list below specifies the diagnostic test time interval that apply to all safety mechanisms provided in this safety manual. If a safety mechanism deviates from the values specified here, it will be specified in the safety mechanism's description.
- single-point fault metric related hardware mechanisms: continuous monitoring (DTTI ≤ 100µs)
- SPFM related software mechanisms expectation is
- once per event (for example read back after configuration, after startup, etc.)
- once per diagnostic test time interval (for example plausibility check of redundant channels)
- latent fault metric related HW mechanisms: once per multiple-point fault detection time interval
- LFM related SW mechanisms: once per multiple-point fault detection time interval
- IFX.Version: 3
- ReqIF-WF.Type: Information

### SCPA-EIAF-IDHF-DJAE: Safe states
A safe state of the application is considered to be an operation mode, in case of a failure, without unreasonable level of risk. Normal operation mode can be considered safe, but not declared a safe state because it is not initiated by a safety measure (see ISO 26262-1:2018 3.131).
Please refer to the safe state support TUCs in the TLSR use cases chapter for more information on safe state support.
- IFX.Version: 8
- ReqIF-WF.Type: Information

#### MCNA-FDFA-CHCJ-FAIF: Considerations for error reactions
Generic error reaction
The safety mechanisms by themselves are in general not able to distinguish whether an error was caused by a transient fault or a permanent fault. Therefore, in specific cases it can make sense to attempt an error recovery, for example by clearing the error condition and restarting the ASIL function. This could be achieved for example by triggering a reset. The safety and security alarm management unit can be configured to request a reset as a reaction to an alarm. Alternatively, the SMU can be configured to trigger a CPU interrupt or an NMI, giving control to the application software which can request a reset after executing some error handling. Additionally, the Fault Signaling Protocol (FSP) pin(s) could be activated to inform the system about an error in the AURIX™ microcontroller. After the reset, the application software should determine whether the fault is permanent or not. If the reset was caused by a transient fault, the software can transition the FSP back to the fault free state and continue operation. If the error analysis detected a permanent error, the affected ASIL function shall be stopped.
Considerations for RAM error handling
During application run-time the safety mechanisms implemented in the RAM instances could detect errors in the RAM data or in the surrounding hardware logic. The following considerations shall be taken into account for the reaction to such alarms:
1. In the case that the a correctable error is reported through the alarm 'VMT Correctable Error', the safety and security alarm management unit can be configured for no reaction.
2. In the case that an uncorrectable error or an address error is reported through the alarm 'VMT Uncorrectable Error', the reaction depends on the ASIL requirements allocated to the function using the RAM :
- For QM functions using the RAM, the system integrator shall evaluate the most appropriate reaction (for example no alarm reaction).
- For ASIL functions using the RAM, upon first occurrence of the error event, the system shall attempt to remove the error condition (for example by reinitializing the RAM contents) and restart the ASIL function. If the same error type happens at the same location again within the same driving cycle, the function which is uses the affected memory instance shall be considered non-operational. The system integrator shall take measures to prevent interference from the non-operational function.
3. In the case that an operational error is reported through the alarm 'VMT Uncorrectable Error' or a miscellaneous error is reported through the alarm 'VMT Miscellaneous Error', the alarm reaction depends on the ASIL requirements allocated to the function using the RAM:
- For QM functions using the RAM, the system integrator shall evaluate the most appropriate reaction (for example no alarm reaction).
- For ASIL functions using the RAM, upon first occurrence of the error event, the system shall attempt to remove the error condition and restart the ASIL function. The system integrator could follow the list of hints for error recovery provided in the VMT chapter of the user manual, sub-chapter 'Alarm handling' section 'Error mapping'. If the same error type happens at the same location again within the same driving cycle, the function which is uses the affected memory instance shall be considered non-operational. The system integrator shall take measures to prevent interference from the non-operational function.
4. The error analysis shall be performed only at module level, that is, using the SRAM Supporting Hardware (SSH) ECCD, ERRINFO and FAULTSTS registers to find the type of error and local address. Error localization at system level, that is, attempting to translate the RAM local address provided in the ETRR register to a system address map address shall be avoided.
Examples:
- The MCAN10 SSH instance has a repeated uncorrectable error within the same driving cycle: then the MCAN0 module shall not be used any further and switched off (prevent interference to the rest of the system). However the CAN1 module (SSH instance MCAN20) or the CAN2 module (SSH instance MCAN21) could still be used.
- The GTM_MCS_* SSH instance has a repeated uncorrectable error withing the same driving cycle: then the MCS shall not be used any further and kept disabled - this includes any usage of the MCS RAM in the context of an ASIL function. However the DPLL can still be used.
Note: For handling of errors detected during MBIST, please refer to the MBIST safety mechanism.
- IFX.Version: 3
- ReqIF-WF.Type: Information

### FNNA-FJHA-IGAA-DBDI: Functional failure modes
Please refer to the AURIX™ TC43x FMEDA sheet for a list and description of the functional failure modes.
- IFX.Version: 4
- ReqIF-WF.Type: Information

### IVYA-EIBB-BEII-BFIE: Safety Mechanisms
The following section shows the safety mechanisms available in this device, clustered by functional block and sorted in alphabetical order.
- IFX.Version: 4
- ReqIF-WF.Type: Information

#### UUAA-EDEA-DAEF-HAEJ: Analog-to-Digital Converter (ADC)
This chapter describes the ADC capabilities as a family specification. Since individual device variants do offer subsets of the described family functionality, the user has to select within the given ADC types and channels. Specific differences to family ADC types and registers can be found in the variant specific ADC Information topic in the User Manual. Package specific channel assignments are documented in the Datasheet.
- IFX.Version: 1
- ReqIF-WF.Type: Information

##### RJXA-FAFD-CJCJ-IECI: Internal safety mechanisms
- IFX.Version: 1
- ReqIF-WF.Type: Information

###### FFPA-EHGE-GBGA-FJHJ: SM[HW]:ADC:RESULT_PLAUSIBILITY
- IFX.Version: 1
- ReqIF-WF.Type: Heading

###### FFPA-EHGE-GBGA-FJHJ_description: Description
The ADC functional block implements a check on the ADC and post processing channel results in hardwre. The results are compared to a configurable threshold by redundant comparator logic. If the ADC detects unexpected results outside the thresholds, it can notify the system.
Each ADC module of TMADC, DSADC, EXMOD, FCC and CDSP provides an independent digital comparator.
For TMADC, DSADC, EXMOD and CDSP a lower and an upper boundary value can get set. FCC allows just one threshold. Threshold values can be updated during run time via a hardware trigger in a deterministic way.
Hardware plausibility check
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The figure above highlights the concept of the hardware plausibility check. The result generated by independent ADC modules is compared by independent digital comparators programmed with independent threshold range. When the configured threshold range is violated, boundary flags are generated by ADC modules (BFL0 and BFL1).
Additionally there is a combining logic which combines these boundary flags. For safety relevant use cases the OR operation can get used, if individual alarm paths are checked for latent faults. In case of a HW fault, the AND operation would mask or delay hardware alarms until all are set. This needs to get avoided. When the boundary flag violation is observed, ADC raises an alarm to SMU.
There are 8 direct alarms between ADC and SMU for this hardware plausibility violation notification. There are up to 62 boundary flags generated within ADC from all instances of TMADC, FCC, DSADC, EXMOD and CDSP. Application Software can configure any two of these up to 62 boundary flags for each alarm generation. This is possible through SM[HW]:ADC:RESULT_PLAUSIBILITY (X=0:7) register.
- ReqIF-WF.Type: Information

###### FFPA-EHGE-GBGA-FJHJ_resetoperationalstate: Reset operational state
After reset all alarms are off.
- ReqIF-WF.Type: Information

###### FFPA-EHGE-GBGA-FJHJ_configurationandactivation: Configuration and activation
Eight alarm signals can be configured through register SM[HW]:ADC:RESULT_PLAUSIBILITY. Alarms can be activated or deactivated in SMU.
- ReqIF-WF.Type: Requirement

###### FFPA-EHGE-GBGA-FJHJ_test: Test
The Application Software shall activate the fault injection mechanism at least once per driving cycle for ADC. It shall then check the generation of the associated alarms.
The error can be injected by changing the threshold range of the digital comparator for independent ADC0 and ADC1 such that boundary condition is violated and the ADC channels generate boundary flags. This will result in an alarms.
The change in threshold range can be done immediately or deterministically by updating the thresholds on hardware trigger.
In addition there is a SM[HW]:ADC:RESULT_PLAUSIBILITY register, where user can simply write and check if the alarms are generated by global alarm generator or not.
- ReqIF-WF.Type: Requirement

###### FFPA-EHGE-GBGA-FJHJ_reporting: Reporting
N.A.
- ReqIF-WF.Type: Information

###### FFPA-EHGE-GBGA-FJHJ_recommendederrorreaction: Recommended error reaction
System integrator to select appropriate safe reaction in SMU.
- ReqIF-WF.Type: Information

###### ARKA-FJFD-JFCH-GCDF: SM[HW]:ADC:CFG_AS_AP
- IFX.Version: 1 1
- ReqIF-WF.Type: Heading

###### ARKA-FJFD-JFCH-GCDF_description: Description
The ADC checks if the access master agent function identifier is enabled for the type of access (read access and write access, configured through the ADC ACCEN registers) to the selected register.
Unauthorized access attempts are blocked by this mechanism.
- ReqIF-WF.Type: Information

###### ARKA-FJFD-JFCH-GCDF_resetoperationalstate: Reset operational state
An application reset will set the configuration of this safety mechanism back to its default value.
- ReqIF-WF.Type: Information

###### ARKA-FJFD-JFCH-GCDF_configurationandactivation: Configuration and activation
This safety mechanism is active after intentional configuration by application software through the ACCENx registers.
- ReqIF-WF.Type: Requirement

###### ARKA-FJFD-JFCH-GCDF_test: Test
This safety measure can be tested after the ACCENx has been configured:
Write access to a protected register by a master agent function that is not the ACCEN owner.
- ReqIF-WF.Type: Requirement

###### ARKA-FJFD-JFCH-GCDF_reporting: Reporting
On detection of an access protection violation on FPI the ADC will terminate the access with FPI error that is detected by the BCU, see SM[HW]:FPI:ERROR_HANDLING.
On detection of an access protection violation on LLI the ADC will terminate the access with LLI error that is detected by the LLI, see SM[HW]:LLI:ERROR_HANDLING.
- ReqIF-WF.Type: Information

###### ARKA-FJFD-JFCH-GCDF_recommendederrorreaction: Recommended error reaction
System integrator to select an appropriate safe reaction in the SMU.
- ReqIF-WF.Type: Information

###### OSPA-FJFD-JFCJ-GHEG: SM[HW]:ADC:SV_AP
- IFX.Version: 5 5
- ReqIF-WF.Type: Heading

###### OSPA-FJFD-JFCJ-GHEG_description: Description
Critical module registers are implemented with a write access restriction that allows access only to masters with supervisor (SV) mode privilege.
Unauthorized access attempts are blocked by this mechanism.
For a list of the registers protected by SV, see tables Register overview – access mode glossary and Register overview – ADC (ascending offset address) in the User Manual.
- ReqIF-WF.Type: Information

###### OSPA-FJFD-JFCJ-GHEG_resetoperationalstate: Reset operational state
The safety mechanism is active after application reset.
- ReqIF-WF.Type: Information

###### OSPA-FJFD-JFCJ-GHEG_configurationandactivation: Configuration and activation
N.A.
- ReqIF-WF.Type: Requirement

###### OSPA-FJFD-JFCJ-GHEG_test: Test
This safety measure can be tested by an write access to a protected register by a master agent function without supervisor (SV) access rights.
- ReqIF-WF.Type: Requirement

###### OSPA-FJFD-JFCJ-GHEG_reporting: Reporting
On detection of an access protection violation on FPI the ADC will terminate the access with FPI error that is detected by the BCU, see SM[HW]:FPI:ERROR_HANDLING.
On detection of an access protection violation on LLI the ADC will terminate the access with LLI error that is detected by the LLI, see SM[HW]:LLI:ERROR_HANDLING.
- ReqIF-WF.Type: Information

###### OSPA-FJFD-JFCJ-GHEG_recommendederrorreaction: Recommended error reaction
System integrator to select an appropriate safe reaction in the SMU.
- ReqIF-WF.Type: Information

###### JOFA-FJFD-JFAF-JCEA: SM[HW]:ADC:SAFETY_ENDINIT
- IFX.Version: 7 7
- ReqIF-WF.Type: Heading

###### JOFA-FJFD-JFAF-JCEA_description: Description
The ADC provides a unique PROT mechanism (SM[HW]:ADC:SAFETY_ENDINIT) that protects the configuration of the access protection mechanism (ACCEN). The ACCEN mechanism is based on the master agent function identifier. This supports freedom from interference of different SW tasks.
Unauthorized access attempts are blocked by this mechanism.
For a list of the registers protected by SM[HW]:ADC:SAFETY_ENDINIT, see tables Register overview – access mode glossary and Register overview – ADC (ascending offset address) in the User Manual.
- ReqIF-WF.Type: Information

###### JOFA-FJFD-JFAF-JCEA_resetoperationalstate: Reset operational state
An application reset will set the configuration of this safety mechanism back to its default value.
- ReqIF-WF.Type: Information

###### JOFA-FJFD-JFAF-JCEA_configurationandactivation: Configuration and activation
This safety mechanism is active after intentional configuration by application software through the SM[HW]:ADC:SAFETY_ENDINIT register.
- ReqIF-WF.Type: Requirement

###### JOFA-FJFD-JFAF-JCEA_test: Test
This safety measure can be tested after the PROT owner has been configured:
Write access to a protected register by a master agent function that is not the PROT owner.
- ReqIF-WF.Type: Requirement

###### JOFA-FJFD-JFAF-JCEA_reporting: Reporting
On detection of an access protection violation on FPI the ADC will terminate the access with FPI error that is detected by the BCU, see SM[HW]:FPI:ERROR_HANDLING.
On detection of an access protection violation on LLI the ADC will terminate the access with LLI error that is detected by the LLI, see SM[HW]:LLI:ERROR_HANDLING.
- ReqIF-WF.Type: Information

###### JOFA-FJFD-JFAF-JCEA_recommendederrorreaction: Recommended error reaction
System integrator to select an appropriate safe reaction in the SMU.
- ReqIF-WF.Type: Information

###### AENA-FJFD-JEHE-DCBJ: SM[HW]:ADC:ENDINIT
- IFX.Version: 1 1
- ReqIF-WF.Type: Heading

###### AENA-FJFD-JEHE-DCBJ_description: Description
The ADC provides a unique PROT mechanism (SM[HW]:ADC:ENDINIT) that protects the configuration of the access protection mechanism (ACCEN). The ACCEN mechanism is based on the master agent function identifier. This supports freedom from interference of different SW tasks.
Unauthorized access attempts are blocked by this mechanism.
For a list of the registers protected by SM[HW]:ADC:ENDINIT, see tables Register overview – access mode glossary and Register overview – ADC (ascending offset address) in the User Manual.
- ReqIF-WF.Type: Information

###### AENA-FJFD-JEHE-DCBJ_resetoperationalstate: Reset operational state
An application reset will set the configuration of this safety mechanism back to its default value.
- ReqIF-WF.Type: Information

###### AENA-FJFD-JEHE-DCBJ_configurationandactivation: Configuration and activation
This safety mechanism is active after intentional configuration by application software through the SM[HW]:ADC:ENDINIT register.
- ReqIF-WF.Type: Requirement

###### AENA-FJFD-JEHE-DCBJ_test: Test
This safety measure can be tested after the PROT owner has been configured:
Write access to a protected register by a master agent function that is not the PROT owner.
- ReqIF-WF.Type: Requirement

###### AENA-FJFD-JEHE-DCBJ_reporting: Reporting
On detection of an access protection violation on FPI the ADC will terminate the access with FPI error that is detected by the BCU, see SM[HW]:FPI:ERROR_HANDLING.
On detection of an access protection violation on LLI the ADC will terminate the access with LLI error that is detected by the LLI, see SM[HW]:LLI:ERROR_HANDLING.
- ReqIF-WF.Type: Information

###### AENA-FJFD-JEHE-DCBJ_recommendederrorreaction: Recommended error reaction
System integrator to select an appropriate safe reaction in the SMU.
- ReqIF-WF.Type: Information

##### TSVA-EHBA-BGJJ-HHFA: Alarms
ADC alarms
| Alarm name | Safety mechanism | Alarm flag to be cleared in |
| --- | --- | --- |
| ADC_SMU_ALARM[7:0] | SM[HW]:ADC_RESULT_PLAUSIBILITY | SMU only |
| FPI Error Alarm | SM[HW]:ADC:SV_AP SM[HW]:ADCI:CFG_AS_AP SM[HW]:ADC:ENDINIT SM[HW]:ADC:SAFETY_ENDINIT | SMU only |
| LLI Bus Error Event Alarm | SM[HW]:ADC:SV_AP SM[HW]:ADC:CFG_AS_AP SM[HW]:ADC:ENDINIT SM[HW]:ADC:SAFETY_ENDINIT | SMU only |
- IFX.Version: 1
- ReqIF-WF.Type: Information

##### BCMA-FAFD-BIID-IEIJ: External safety mechanisms
- IFX.Version: 1
- ReqIF-WF.Type: Information

###### MMEA-EHGC-GGJC-EBBE: ESM[SW]:ADC:MODULE_REDUNDANCY
- IFX.Version: 14
- ReqIF-WF.Type: Heading

###### MMEA-EHGC-GGJC-EBBE_description: Description
Faults in the functions of ADC can be detected by implementing analog to digital conversion over two independent channels. Independent channels could be homogeneous or heterogeneous.
The Application Software shall use two or more diverse or redundant ADC and post processing channels with independent ADC and post processing modules.
ADC redundancy
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Figure above highlights the basic principle of ADC redundancy. The scope of redundancy also includes that independent analog pins are used. Details of which analog pins are considered is available in package safety manual section.
The ADCs selected from different Safety Groups as highlighted above can be considered as mission and monitoring channels which are physically separated to ensure no dependency. The configuration of both channels is responsibility of the user and depends on the application.
The Application Software shall compare the results of mission and monitoring channels. The redundant signal chains will not perfectly match each other due to variations within the operating conditions or different operating boundaries (diverse redundancy). Limits have to be set considering system requirements.
ADC redundancy ranges
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The figure above does illustrate ranges. Monitoring boundaries have to be set to avoid a Potential Violation of Safety Goal (PVSG). Variation of measurements within the monitoring boundaries may result in performance degradation but must not violate a primary safety goal. The actual values that are tolerable and do not cause a PVSG depend on the system and can be determined considering the item-level only.
The safety application where hardware trigger comes from other peripherals to ADC controls different function of the ADC, hardware triggers shall be safe and require a safety mechanism as well. The Application Software shall use two diverse or redundant triggers on two diverse or redundant ADC modules with physically separated trigger sources.
Note: The redundant triggers are laid out using separate physical triggers with a defined minimum distance between two triggers.
There are up to 64 triggers coming from different peripherals to ADC. The other peripherals are PORTS, SCU (ERU), GTM and eGTM. Same 64 triggers are received by every ADC module where a trigger based functionality is required.
- ReqIF-WF.Type: Requirement

###### GVTA-EHGE-GAGD-HBBE: ESM[SW]:ADC:RESULT_PLAUSIBILITY
- IFX.Version: 1
- ReqIF-WF.Type: Heading

###### GVTA-EHGE-GAGD-HBBE_description: Description
In addition to the functional redundancy, consistency monitoring is required to detect any faults in the analog to digital conversion
The Application Software shall compare the redundant ADCs and post processed channel results against application constraints. For example against the physically possible changes of the sensed values between measurements. If the Application Software detects unexpected results during these checks, it shall notify the system about the presence of a fault. As show in Figure 1, both the diverse redundant channels generate their independent results. Application Software shall read these results and do a plausibility check against the application limits on these results. If the results are outside the expected range, software shall notify the system about the faults.
Note: Result Plausibility check includes results from TMADC, DSADC, EXMOD and CDSP result registers. In addition for the applications where boundary flag serve as a result, Application Software can compare the boundary events from diverse or redundant channel.
- ReqIF-WF.Type: Requirement

###### IEEA-EHGD-GCFE-EBJI: ESM[SW]:ADC:VAREF_PLAUSIBILITY
- IFX.Version: 11
- ReqIF-WF.Type: Heading

###### IEEA-EHGD-GCFE-EBJI_description: Description
To allow Application Software to enable independent ADC operation, Application Software shall perform plausibility check on VAREF as independent ADC module can be connected to one common VAREF pin.
The Application Software shall implement a check of the ADC reference voltage (VAREF) either by an external monitor or by internally converting a known signal and compare the result with expected value. This check shall be executed at least once per driving cycle or better periodically after a predefined time or number of conversions. If the Application Software detects unexpected results during these checks, it shall notify the system about the presence of a fault.
Internal conversion of a known voltage is possible in TMADC. In each TMADC there are two monitoring samplers, with each monitoring sampler connected to each core inside TMADC. Internal generated voltages from the band gap are mapped on these monitoring samplers. These voltages are VDDK0 and VDDK1. Alternatively the PMS reference equivalent can get selected on MCH0IN1 (PMS_ADC_REF).
With the help of monitoring sampler(s), the Application Software can convert these voltages by using the analog reference voltage. The conversion result can be read from monitoring sampler result register inside TMADC. On this result value, Application Software shall perform a plausibility check to see if the converted result is in the expected range. Result in the expected range does imply correctness of the VAGND level and POWER_STATUS setting (3 V or 5 V operation).
Note: The defined safety mechanism is only possible in TMADC and not in FCC and DSADC. FCC shares same analog reference pin with TMADC. Therefore VDDK0 or VDDK1 measurement in TMADC ensures that the FCC connected to same VAREF also receives analog reference. This does not cover the path between VAREF pin and FCC in this case. DSADC also shares same VAREF in some package variants. This safety mechanism excludes VAREF level as common cause fault initiator. Internal connectivity requires ESM[SW]:RESULT_PLAUSIBILITY in addition.
- ReqIF-WF.Type: Requirement

###### PZUA-FAIA-HICH-JEDC: ESM[SW]:ADC:BROKEN_WIRE_DETECTION
The Application Software shall implement broken wire detection diagnostics on all single physical inputs (single package pin) used by diverse or homogenous redundant ADCs. If the Application Software detects unexpected results during these checks, it shall notify the system about the presence of a fault.
A single physical input is converted by redundant MCU internal ADCs. The use case Safe 'Single Input Analog Acquisition' does consider reduced ASIL metric [ASIL B], but is still useful for many applications.
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The MCU provides additional pull-up and pull-down current sources as shown in the figure above. The channel input is pulled up or down depending on the configuration, with the enabled current source during the complete sampling phase.
The application software shall verify the expected behavior on the channel input with subsequent data reads on the channel conversion result
1. With pull-up or pull-down current source enabled and forcing a gradual change in the conversion result.
2. After disabling current source showing the recovery of the conversion result to the expected sensor driven value. Slow or no recovery is an indication for broken or degraded connection
The expected behavior is a function of the sensor's current, channel's total sampling time and the channel capacitance. User needs to characterize the signal path external to the MCU and to determine individual pass/fail comparison limits for the system. For further details please refer to the User Manual.
- IFX.Version: 9
- ReqIF-WF.Type: Heading

###### PBYA-EHHE-GCJC-EJDB: ESM[SW]:ADC:ISR_MONITOR
- IFX.Version: 12
- ReqIF-WF.Type: Heading

###### PBYA-EHHE-GCJC-EJDB_description: Description
This ESM shall detect missing or unintended interrupts originating from the ADC module. All ADC use cases count on converter redundancy. The situation regarding the interrupts does differ and the ESM regarding the need for usage of interrupts in this FB depends on the use cases and code implementation.
Use Case 1: Homogenous redundant ADC channels :
Two independent ADC modules of the same type can be used to convert the same analog signal to its digital representation in a redundant way. Independence requires allocating channels from 2 different ADC modules (e.g. 2 of DSADC, 2 of TMADC) instances.
Each ADC shall be configured to operate in the same way and thus generate the same interrupts within a tolerance time window. To detect missing or unintended interrupts, the application software shall check if the interrupts arriving from one of the ADC modules are also arriving from the second ADC module within the time tolerance window. If the presence of only one of the interrupts is detected at any given time, the Application Software shall trigger an error signal and an appropriate reaction.
Use Case 2: Diverse redundant ADC channels :
Two independent ADC channels can be used to convert the same analog signal to its digital representation in a redundant way. Diverse redundancy is reached, when comparing the results of different converter types.
The TMADC, DSADC or FCC channels shall be configured to operate in a similar way and thus generate similar interrupts within a tolerance time window. To detect missing or unintended interrupts, the Application Software shall check if the interrupts arriving from one of the ADC channels are also arriving from the second ADC channel within the time tolerance window. If the presence of only one of the interrupts is detected at any given time, the Application Software shall trigger an error signal and an appropriate reaction.
Use Case 3: Single Input redundant ADC Channels
Here a single physical path and package pin is the input of an analog signal. Two independent ADCs convert the same analog signal to its digital representation. Fan-out to independent ADCs is internal to the MCU. This is either two independent TMADCs or a diverse combination of TMADC, DSADC or FCC channels.
The ADCs shall be configured to operate in a similar way and thus generate similar interrupts within a tolerance time window. To detect missing or unintended interrupts, the Application Software shall check if the interrupts arriving from one of the ADC channels are also arriving from the second ADC channel within the time tolerance window. If the presence of only one of the interrupts is detected at any given time, the Application Software shall trigger an error signal and an appropriate reaction.
Interrupts
Possible interrupt signals are ADC_IR_SRC_TMADCxSR[5:0], ADC_IR_SRC_FCCxSR[1:0], ADC_IR_SRC_DSADCxSR[3:0] and ADC_IR_SRC_EXMODxSR[3:0]. If used as redundant in the safety context, they need to indicate equal or similar events. This could be events showing the availability of results or events indicating the result is crossing a certain boundary.
To detect missing or unintended interrupts, the Application Software shall check the status of the redundant ADC whenever one converter signals an interrupt. Given some uncertainty in the interrupt generation especially when the converter types do differ, a plausibility check based on the status of the other ADC (that is, conversion result matches within a small tolerance) is sufficient.
Other interrupts
Not applicable, since the use cases formulate the need of redundancy. All safety relevant interrupts need an equivalent or similar event for comparison.
Common for all use cases:
The Application Software shall disable any interrupts not used in the ESM[SW]:ADC:ISR_MONITOR.EVEN, FCCx_SRCFG.SRnEVSEL, DSADC_INx_SRCFG.SRnE and corresponding registers for the service request in the Interrupt Router (IR) bitfields.
- ReqIF-WF.Type: Requirement

###### PBYA-EHHE-GCJC-EJDB_section2
- ReqIF-WF.Type: Information

###### PBYA-EHHE-GCJC-EJDB_section3
- ReqIF-WF.Type: Information

###### KEJA-FBGF-ECAF-IADH: ESM[SW]:ADC:CONFIG_READBACK
The following registers of the ADC configuration have to be read back after write. The read back values have to be compared with the written values. In case of any difference the Application Software shall trigger a reaction:
- ESM[SW]:ADC:CONFIG_READBACK
- ESM[SW]:ADC:CONFIG_READBACK
- ESM[SW]:ADC:CONFIG_READBACK
- ETBFxSEL
- ESM[SW]:ADC:CONFIG_READBACK
- ESM[SW]:ADC:CONFIG_READBACK
- IFX.Version: 1
- ReqIF-WF.Type: Heading

#### FICA-EDCJ-DABF-JEHA: Asynchronous/Synchronous Interface (ASCLIN)
The ASCLIN module provides asynchronous serial communication with external devices using only data-in and data-out signals. The focus of the module is for fast and flexible communication, either as fast point-to-point using ASC protocol or master-to-many slaves communication using the LIN protocol. ASCLIN supports also the synchronous SPI communication.
- ReqIF-WF.Type: Information

##### ZIGA-FAFE-IGEI-ACHF: Internal safety mechanisms
- IFX.Version: 1
- ReqIF-WF.Type: Information

###### VVNA-EHHJ-EBJJ-HAHC: SM[HW]:ASCLIN:ENDINIT
- IFX.Version: 1 1
- ReqIF-WF.Type: Heading

###### VVNA-EHHJ-EBJJ-HAHC_description: Description
The ASCLIN provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – ASCLIN (ascending offset address) in the User Manual.
- ReqIF-WF.Type: Information

###### VVNA-EHHJ-EBJJ-HAHC_resetoperationalstate: Reset operational state
An application reset will set the configuration of this safety mechanism back to its default value.
- ReqIF-WF.Type: Information

###### VVNA-EHHJ-EBJJ-HAHC_configurationandactivation: Configuration and activation
This safety mechanism is active after intentional configuration by application software through the PROTE register.
- ReqIF-WF.Type: Requirement

###### VVNA-EHHJ-EBJJ-HAHC_test: Test
This safety measure can be tested after the PROT owner has been configured:
Write access to a protected register by a master agent function that is not the PROT owner.
- ReqIF-WF.Type: Requirement

###### VVNA-EHHJ-EBJJ-HAHC_reporting: Reporting
On detection of an access protection violation the ASCLIN will terminate the access with FPI error that is detected by the BCU, see SM[HW]:FPI:ERROR_HANDLING.
- ReqIF-WF.Type: Information

###### VVNA-EHHJ-EBJJ-HAHC_recommendederrorreaction: Recommended error reaction
System integrator to select an appropriate safe reaction in the SMU.
- ReqIF-WF.Type: Information

###### VPHA-EHHJ-EBJJ-IBHE: SM[HW]:ASCLIN:SAFETY_ENDINIT
- IFX.Version: 1 1
- ReqIF-WF.Type: Heading

###### VPHA-EHHJ-EBJJ-IBHE_description: Description
The ASCLIN provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – ASCLIN (ascending offset address) in the User Manual.
- ReqIF-WF.Type: Information

###### VPHA-EHHJ-EBJJ-IBHE_resetoperationalstate: Reset operational state
An application reset will set the configuration of this safety mechanism back to its default value.
- ReqIF-WF.Type: Information

###### VPHA-EHHJ-EBJJ-IBHE_configurationandactivation: Configuration and activation
This safety mechanism is active after intentional configuration by application software through the PROTSE register.
- ReqIF-WF.Type: Requirement

###### VPHA-EHHJ-EBJJ-IBHE_test: Test
This safety measure can be tested after the PROT owner has been configured:
Write access to a protected register by a master agent function that is not the PROT owner.
- ReqIF-WF.Type: Requirement

###### VPHA-EHHJ-EBJJ-IBHE_reporting: Reporting
On detection of an access protection violation the ASCLIN will terminate the access with FPI error that is detected by the BCU, see SM[HW]:FPI:ERROR_HANDLING.
- ReqIF-WF.Type: Information

###### VPHA-EHHJ-EBJJ-IBHE_recommendederrorreaction: Recommended error reaction
System integrator to select an appropriate safe reaction in the SMU.
- ReqIF-WF.Type: Information

###### ABKA-EHHJ-EBJJ-HGEF: SM[HW]:ASCLIN:CFG_AS_AP
- IFX.Version: 4 4
- ReqIF-WF.Type: Heading

###### ABKA-EHHJ-EBJJ-HGEF_description: Description
The ASCLIN checks if the access master agent function identifier is enabled for the type of access (read access and write access, configured through the ASCLIN ACCEN registers) to the selected register.
Unauthorized access attempts are blocked by this mechanism.
- ReqIF-WF.Type: Information

###### ABKA-EHHJ-EBJJ-HGEF_resetoperationalstate: Reset operational state
An application reset will set the configuration of this safety mechanism back to its default value.
- ReqIF-WF.Type: Information

###### ABKA-EHHJ-EBJJ-HGEF_configurationandactivation: Configuration and activation
This safety mechanism is active after intentional configuration by application software through the ACCENx registers.
- ReqIF-WF.Type: Requirement

###### ABKA-EHHJ-EBJJ-HGEF_test: Test
This safety measure can be tested after the ACCENx has been configured:
Write access to a protected register by a master agent function that is not the ACCEN owner.
- ReqIF-WF.Type: Requirement

###### ABKA-EHHJ-EBJJ-HGEF_reporting: Reporting
On detection of an access protection violation the ASCLIN terminate the access with FPI error that is detected by the BCU, see SM[HW]:FPI:ERROR_HANDLING.
- ReqIF-WF.Type: Information

###### ABKA-EHHJ-EBJJ-HGEF_recommendederrorreaction: Recommended error reaction
System integrator to select an appropriate safe reaction in the SMU.
- ReqIF-WF.Type: Information

###### ZVZA-EHHJ-EBJJ-FECF: SM[HW]:ASCLIN:SV_AP
- IFX.Version: 5 5
- ReqIF-WF.Type: Heading

###### ZVZA-EHHJ-EBJJ-FECF_description: Description
Critical module registers are implemented with a write access restriction that allows access only to masters with supervisor (SV) mode privilege.
Unauthorized access attempts are blocked by this mechanism.
For a list of the registers protected by SV, see tables Register overview – access mode glossary and Register overview – ASCLIN (ascending offset address) in the User Manual.
- ReqIF-WF.Type: Information

###### ZVZA-EHHJ-EBJJ-FECF_resetoperationalstate: Reset operational state
The safety mechanism is active after application reset.
- ReqIF-WF.Type: Information

###### ZVZA-EHHJ-EBJJ-FECF_configurationandactivation: Configuration and activation
N.A.
- ReqIF-WF.Type: Requirement

###### ZVZA-EHHJ-EBJJ-FECF_test: Test
This safety measure can be tested by an write access to a protected register by a master agent function without supervisor (SV) access rights.
- ReqIF-WF.Type: Requirement

###### ZVZA-EHHJ-EBJJ-FECF_reporting: Reporting
On detection of an access protection violation the ASCLIN will terminate the access with FPI error that is detected by the BCU, see SM[HW]:FPI:ERROR_HANDLING.
- ReqIF-WF.Type: Information

###### ZVZA-EHHJ-EBJJ-FECF_recommendederrorreaction: Recommended error reaction
System integrator to select an appropriate safe reaction in the SMU.
- ReqIF-WF.Type: Information

##### KNJA-EHBJ-DFDA-DAJB: Alarms
ASCLIN alarms
| Alarm name | Safety mechanism | Alarm flag to be cleared in |
| --- | --- | --- |
| FPI error alarm | SM[HW]:ASCLIN:SV_AP SM[HW]:ASCLIN:CFG_AS_AP SM[HW]:ASCLIN:ENDINIT SM[HW]:ASCLIN:SAFETY_ENDINIT | SMU only |
- IFX.Version: 1
- ReqIF-WF.Type: Information

##### YQDA-FAFE-IGEA-AEEG: External safety mechanisms
- IFX.Version: 1
- ReqIF-WF.Type: Information

###### IBUA-EHEE-GFAE-FGCH: ESM[SW]:ASCLIN:SAFE_COMMUNICATION
- IFX.Version: 9
- ReqIF-WF.Type: Heading

###### IBUA-EHEE-GFAE-FGCH_description: Description
Random hardware faults in the communication controller or in the communication interface can lead to corruption or loss of safety related data carried by a communication frame. In-order to detect the causes or effects of such communication faults, the application software has to implement safe End-to-End communication protecting the safety critical data.
The Safe End-to-End communication has to be implemented by application software of both the sender and the receiver of a communication frame. The sender appends an "E2E header" containing safety elements such as CRC or Counter to the communication data. The receivers evaluates the safety elements contained in the E2E header of the communication frame in order to detect faults. Figure below shows an example layout and construction of a communication frame protected by Safe End-to-End communication.
Safe end-to-end communication
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The following section describes the safety elements contained in the E2E header
Cyclic redundancy check (CRC)
The CRC is calculated by the sender for the contents of the safety critical communication data. The CRC protects against data corruption. The user is responsible for choosing an appropriate CRC polynomial with sufficient Hamming Distance to provide required error detection capability for a corresponding length of communication data. It is recommended to use a different CRC polynomial 1that the one used by the communication controller (if any) to provide redundancy. The receiver evaluates the CRC in the E2E header of the received communication frame to detect data corruption. A mismatch of the computed CRC value compared to the received CRC value indicates occurrence of data corruption.
1Hint: AUTOSAR Specification of SW-C End-to-End Communication Protection Library Release 4.3.1 recommends CRC polynomials to be used for various length of application data.
Counter
The Counter enables to detect faults such as loss of data, repetition of data. The sender for a given application data, inserts a counter value to the E2E header. The counter value is incremented for every transmission of the application data. The receiver evaluates the counter value in the E2E header of the received communication frame with an expected counter value. The following error scenarios can be detected
- Repetition of frame - The received counter values is same as that of the previous counter value
- Loss of frame(s) - The received counter value is non-consecutive
The receiver upon successful evaluation of the received communication frame increments the corresponding current counter value.
Note: The user is responsible for implementing counter synchronization methods between the sender and receiver.
The application software can combine the counter value with a timer to detect delayed communication or block in the communication interface. Example: a timer (for example the system timer (STM)) can be configured to trigger a periodic check of the counter value of the associated application data. If the counter value does not change for a given time interval (for example within an FTTI), then delayed communication or block in communication is detected.
- ReqIF-WF.Type: Requirement

###### YCPA-EHEE-GFEB-JEBH: ESM[SW]:ASCLIN:CHANNEL_REDUNDANCY
- IFX.Version: 12
- ReqIF-WF.Type: Heading

###### YCPA-EHEE-GFEB-JEBH_description: Description
Faults in the following functions of ASCLIN can be detected by implementing ASC/LIN/SPI communication over 2 independent channels triggered by independent transmit triggers
- Transmit: The ASCLIN receives data from application software and sends it to an external ASCLIN device
- Transmit Trigger only for ASC communication: The ASCLIN initiates transmission of ASC frame upon a trigger from GTM or eGTM
- Receive: The ASCLIN receives data from an external ASCLIN device and routes it to application software for further processing
The figure below shows an illustration for implementing a redundant ASCLIN communication channel. One of the redundant ASC/LIN/UART communication channel can be assigned as "Mission" channel (highlighted in Blue) and the other can be used as a "Monitoring" channel (highlighted in green)
ASCLIN channel redundancy
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In-order to prevent common cause faults, the redundant ASCLIN communication channels have to be independent of each other. This can be achieved by
- Using separate ASCLIN modules as Mission and Monitoring communication channel
- Both channels need to have similar configuration
- Other supporting blocks (for example PORTS) need to be configured similarly to enable the communication, for example driver strength and pull-up
- Using independent transmit trigger sources from GTM or eGTM for the mission and monitoring communication channel
- Using independent package pins and PORTS instances
Please refer to the chapter “Safety related information for package” of the safety manual to find out which pins and modules are independent of each other.
Reception of data
As soon as one of the channels receives a frame a synchronization mechanism needs to be triggered. If this synchronization identifies two matching packets, then the lockstep CPU needs to compare the packet content. If the content of Mission- and Monitoring channel match within an FTTI, then the data is considered as safe. The data comparison may optionally contain application level plausibility checks on result value bounds.
Possible synchronization techniques are:
1. Flag based synchronization
On receiving a frame a corresponding flag is set (Mission flag or Monitoring flag)
- If both flags are set within FTTI, then synchronization is OK. This situation will trigger frame comparison and flag reset
- If only one flag is set at the end of FTTI and the corresponding channel receives another packet, this is an error
2. Packet number
On receiving a frame a corresponding counter is increased (Mission counter or Monitoring counter)
- If the counters match within FTTI, then synchronization is OK and a comparison can be triggered
- If the counters have a difference greater than one at the end of FTTI, then an error has occurred
3. Timestamp from system timer
Each channel features a timestamp variable (Mission timestamp or Monitoring timestamp) stored on safe memory (for example DSPR).
- Both timestamp variables are initialized with a value equal to zero
- On receiving a frame the corresponding timestamp variables (Mission timestamp and Monitoring timestamp) are updated from a safe timer (for example System Timer (STM))
- As soon as both timestamp variables are different to zero a comparison by lockstep CPU of frame data and time window is triggered. This also sets both timestamp variables to zero
- If a channel receives a frame and its corresponding timestamp variable is not zero, then an error is detected
- If the timestamp variable values differ by more than a predefined time window, then an error is detected
- The system integrator shall ensure that the timestamp variables are checked at least once per FTTI, either with a periodic trigger or by ensuring that the message rate is at least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
Upon detection of an error the application software shall trigger an appropriate reaction.
Transmission of data
The application SW prepares frames containing the same data on Mission and Monitoring channel. Then both channels are triggered.
Interrupts
If the application software uses interrupts of ASCLIN to service the mission and monitoring channel then to detect missing or unintended interrupts, the application software shall check if the interrupts arriving from mission channel are also arriving from the monitoring channel within an FTTI. If the presence of only one of the interrupts is detected at end of the FTTI, the application software shall trigger an error signal and an appropriate reaction.
- ReqIF-WF.Type: Requirement

###### DVTA-EHHE-GBAH-DEGG: ESM[SW]:ASCLIN:ISR_MONITOR
- IFX.Version: 7
- ReqIF-WF.Type: Heading

###### DVTA-EHHE-GBAH-DEGG_description: Description
This ESM shall detect missing or unintended interrupts originating from the ASCLIN module.
Transmit / Receive interrupts
The ASCLIN module signals to the application software that a message was received by triggering the interrupt ASCLINx_FLAGS.RH, ASCLINx_FLAGS.RR, ASCLINx_FLAGS.RFL (x=0-28). Similarly, a transmitted message is signaled by triggering the interrupt ASCLINx_FLAGS.TH, ASCLINx_FLAGS.TR, ASCLINx_FLAGS.TC, ASCLINx_FLAGS.TFL (x=0-28). To detect individual missing or unintended send or receive interrupts, the system integrator shall use the properties of the ESM[SW]:ASCLIN:SAFE_COMMUNICATION (e.g. timestamp or frame counter). For example, a repeated receive frame counter value indicates that an unintended receive interrupt has occurred. Interrupts missing altogether are covered by the timeout mechanism of the ESM[SW]:ASCLIN:SAFE_COMMUNICATION.
Upon detection of a missing or unintended interrupt, the application software shall trigger a safe reaction.
Other interrupts:
Other interrupts originating from the ASCLIN module can be used if the system integrator wishes to do so. These are: ASCLINx_FLAGS.TFE, ASCLINx_FLAGS.OMT, ASCLINx_FLAGS.HT, ASCLINx_FLAGS.RT, ASCLINx_FLAGS.RFO, ASCLINx_FLAGS.RFU, ASCLINx_FLAGS.TFU, ASCLINx_FLAGS.CE, ASCLINx_FLAGS.OMT, ASCLINx_FLAGS.FED, ASCLINx_FLAGS.RED, ASCLINx_FLAGSE.BD, ASCLINx_FLAGS.PE, ASCLINx_FLAGS.LA, ASCLINx_FLAGS.LP, ASCLINx_FLAGS.LC, ASCLINx_FLAGS.FE (x=0-28). Errors in the communication due to unintended or missing interrupts of this type are also covered by ESM[SW]:ASCLIN:SAFE_COMMUNICATION.
Unused interrupts:
If the system integrator decides not to use certain interrupts, these shall be disabled in the ASCLINx_FLAGSENABLE register and in the corresponding interrupt router SRC register.
- ReqIF-WF.Type: Requirement

#### EUKA-EDCJ-CIIE-BBFB: Controller Area Network interface (CAN)
The CAN module provides a communication interface according to the ISO 11898-1 standard, supporting both classical CAN and CAN FD communication. It provides the CAN Routing Engine as an extension which is used to route data within different CAN nodes based on the CAN-ID, and it also provides a virtual host interface to the RxFIFOs and TxQueues/TxFIFO of M_CAN. The CAN module in this document is referred as MCMCAN.
- IFX.Version: 1
- ReqIF-WF.Type: Information

##### CIYA-FAFE-IEJF-IJDH: Internal safety mechanisms
- IFX.Version: 1
- ReqIF-WF.Type: Information

###### YCVA-EHHJ-FCFE-BBEA: SM[HW]:CAN:SV_AP
- IFX.Version: 5 5
- ReqIF-WF.Type: Heading

###### YCVA-EHHJ-FCFE-BBEA_description: Description
Critical module registers are implemented with a write access restriction that allows access only to masters with supervisor (SV) mode privilege.
Unauthorized access attempts are blocked by this mechanism.
For a list of the registers protected by SV, see tables Register overview – access mode glossary and Register overview – CAN (ascending offset address) in the User Manual.
- ReqIF-WF.Type: Information

###### YCVA-EHHJ-FCFE-BBEA_resetoperationalstate: Reset operational state
The safety mechanism is active after application reset.
- ReqIF-WF.Type: Information

###### YCVA-EHHJ-FCFE-BBEA_configurationandactivation: Configuration and activation
N.A.
- ReqIF-WF.Type: Requirement

###### YCVA-EHHJ-FCFE-BBEA_test: Test
This safety measure can be tested by an write access to a protected register by a master agent function without supervisor (SV) access rights.
- ReqIF-WF.Type: Requirement

###### YCVA-EHHJ-FCFE-BBEA_reporting: Reporting
On detection of an access protection violation the CAN will terminate the access with FPI error that is detected by the BCU, see SM[HW]:FPI:ERROR_HANDLING.
- ReqIF-WF.Type: Information

###### YCVA-EHHJ-FCFE-BBEA_recommendederrorreaction: Recommended error reaction
System integrator to select an appropriate safe reaction in the SMU.
- ReqIF-WF.Type: Information

###### TRBA-EHHJ-FCFE-EBJC: SM[HW]:CAN:SAFETY_ENDINIT
- IFX.Version: 7 7
- ReqIF-WF.Type: Heading

###### TRBA-EHHJ-FCFE-EBJC_description: Description
The CAN provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – CAN (ascending offset address) in the User Manual.
- ReqIF-WF.Type: Information

###### TRBA-EHHJ-FCFE-EBJC_resetoperationalstate: Reset operational state
An application reset will set the configuration of this safety mechanism back to its default value.
- ReqIF-WF.Type: Information

###### TRBA-EHHJ-FCFE-EBJC_configurationandactivation: Configuration and activation
This safety mechanism is active after intentional configuration by application software through the PROTSE register.
- ReqIF-WF.Type: Requirement

###### TRBA-EHHJ-FCFE-EBJC_test: Test
This safety measure can be tested after the PROT owner has been configured:
Write access to a protected register by a master agent function that is not the PROT owner.
- ReqIF-WF.Type: Requirement

###### TRBA-EHHJ-FCFE-EBJC_reporting: Reporting
On detection of an access protection violation the CAN will terminate the access with FPI error that is detected by the BCU, see SM[HW]:FPI:ERROR_HANDLING.
- ReqIF-WF.Type: Information

###### TRBA-EHHJ-FCFE-EBJC_recommendederrorreaction: Recommended error reaction
System integrator to select an appropriate safe reaction in the SMU.
- ReqIF-WF.Type: Information

###### SFYA-EHHJ-FCFE-CICC: SM[HW]:CAN:ENDINIT
- IFX.Version: 1 1
- ReqIF-WF.Type: Heading

###### SFYA-EHHJ-FCFE-CICC_description: Description
The CAN provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – CAN (ascending offset address) in the User Manual.
- ReqIF-WF.Type: Information

###### SFYA-EHHJ-FCFE-CICC_resetoperationalstate: Reset operational state
An application reset will set the configuration of this safety mechanism back to its default value.
- ReqIF-WF.Type: Information

###### SFYA-EHHJ-FCFE-CICC_configurationandactivation: Configuration and activation
This safety mechanism is active after intentional configuration by application software through the PROTE register.
- ReqIF-WF.Type: Requirement

###### SFYA-EHHJ-FCFE-CICC_test: Test
This safety measure can be tested after the PROT owner has been configured:
Write access to a protected register by a master agent function that is not the PROT owner.
- ReqIF-WF.Type: Requirement

###### SFYA-EHHJ-FCFE-CICC_reporting: Reporting
On detection of an access protection violation the CAN will terminate the access with FPI error that is detected by the BCU, see SM[HW]:FPI:ERROR_HANDLING.
- ReqIF-WF.Type: Information

###### SFYA-EHHJ-FCFE-CICC_recommendederrorreaction: Recommended error reaction
System integrator to select an appropriate safe reaction in the SMU.
- ReqIF-WF.Type: Information

###### OHGA-EHHJ-FCFE-DFDE: SM[HW]:CAN:CFG_AS_AP
- IFX.Version: 5 5
- ReqIF-WF.Type: Heading

###### OHGA-EHHJ-FCFE-DFDE_description: Description
The CAN checks if the access master agent function identifier is enabled for the type of access (read access and write access, configured through the CAN ACCEN registers) to the selected register.
Unauthorized access attempts are blocked by this mechanism.
- ReqIF-WF.Type: Information

###### OHGA-EHHJ-FCFE-DFDE_resetoperationalstate: Reset operational state
An application reset will set the configuration of this safety mechanism back to its default value.
- ReqIF-WF.Type: Information

###### OHGA-EHHJ-FCFE-DFDE_configurationandactivation: Configuration and activation
This safety mechanism is active after intentional configuration by application software through the ACCENx registers.
- ReqIF-WF.Type: Requirement

###### OHGA-EHHJ-FCFE-DFDE_test: Test
This safety measure can be tested after the ACCENx has been configured:
Write access to a protected register by a master agent function that is not the ACCEN owner.
- ReqIF-WF.Type: Requirement

###### OHGA-EHHJ-FCFE-DFDE_reporting: Reporting
On detection of an access protection violation the CAN will terminate the access with FPI error that is detected by the BCU, see SM[HW]:FPI:ERROR_HANDLING.
- ReqIF-WF.Type: Information

###### OHGA-EHHJ-FCFE-DFDE_recommendederrorreaction: Recommended error reaction
System integrator to select an appropriate safe reaction in the SMU.
- ReqIF-WF.Type: Information

##### APIA-EHBJ-DDHI-BBFC: Alarms
CAN alarms
| Alarm name | Safety mechanism | Alarm flag to be cleared in |
| --- | --- | --- |
| FPI error alarm | SM[HW]:CAN:SV_AP SM[HW]:CAN:CFG_AS_AP SM[HW]:CAN:ENDINIT SM[HW]:CAN:SAFETY_ENDINIT | SMU only |
- IFX.Version: 1
- ReqIF-WF.Type: Information

##### FRCA-FAFE-IEAB-CGAD: External safety mechanisms
- IFX.Version: 1
- ReqIF-WF.Type: Information

###### NJSA-EHHE-GBJF-HAJJ: ESM[SW]:CAN:ISR_MONITOR
- IFX.Version: 1
- ReqIF-WF.Type: Heading

###### NJSA-EHHE-GBJF-HAJJ_description: Description
This ESM shall detect missing or unintended interrupts originating from the CAN module.
Transmit/receive interrupts
The CAN module signals to the application software that a message was received by triggering the interrupts Ni_IR.RF0N, Ni_IR.RF1N,Ni_IR.RF1W , Ni_IR.DRX, Ni_CRE_IR.RBUF0I and Ni_CRE_IR.RBUF1I. Similarly, a transmitted message is signaled by triggering the interrupts Ni_IR.TCF, Ni_IR.TC, Ni_IR.HPM, Ni_IR.TEFN, Ni_IR.TEFF, Ni_IR.TEFW and Ni_CRE_IR.TBUFI. To detect individual missing or unintended send or receive interrupts, the system integrator shall use the properties of the safe E2E communication (e.g. timestamp or frame counter). For example, a repeated receive frame counter value indicates that an unintended receive interrupt has occurred. Interrupts missing altogether are covered by the timeout mechanism of the safe E2E communication.
Upon detection of a missing or unintended interrupt, the application software shall trigger an appropriate reaction.
Other interrupts
Other interrupts originating from the CAN module can be used if the system integrator wishes to do so. These are: Ni_IR.ELO, Ni_IR.BO, Ni_IR.STE, Ni_IR.WDI, Ni_IR.FOW, Ni_IR.ACKE, Ni_IR.BE, Ni_IR.CRCE, Ni_IR.MRAF, Ni_IR.EW, Ni_IR.EP, Ni_IR.TSW, Ni_IR.RF0L, Ni_IR.RF1L, Ni_IR.TEFL, Ni_IR.TFE, Ni_IR.RF0F, Ni_IR.RF1F, Ni_IR.TOO, MESTAT.CAPE, Ni_CRE_IR.SFRMLI and Ni_CRE_IR.XFRMLI. Errors in the communication due to unintended or missing interrupts of this type are also covered by safe E2E communication.
Unused interrupts:
If the system integrator decides not to use certain interrupts, these shall be disabled in the Ni_IE (i=0-3), Ni_TIMER_RXTOUT (i=0-3), Ni_CRE_HBUF_RXz_CONFIG (i=0-3;z=0-1), Ni_IDMU_FRTCONFIG (i=0-3) and MECR registers and in the interrupt router SRC register.
- ReqIF-WF.Type: Requirement

###### PLMA-FJJB-DDEH-CDFD: ESM[SW]:CAN:SAFE_COMMUNICATION
- IFX.Version: 1
- ReqIF-WF.Type: Heading

###### PLMA-FJJB-DDEH-CDFD_description: Description
Random hardware faults in the communication controller or in the communication interface can lead to corruption or loss of safety related data carried by a communication frame. In-order to detect the causes or effects of such communication faults, the application software has to implement safe End-to-End communication protecting the safety critical data.
The Safe End-to-End communication has to be implemented by application software of both the sender and the receiver of a communication frame. The sender appends an "E2E header" containing safety elements such as CRC or Counter to the communication data. The receivers evaluates the safety elements contained in the E2E header of the communication frame in order to detect faults. Figure below shows an example layout and construction of a communication frame protected by Safe End-to-End communication.
Safe end-to-end communication
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The following section describes the safety elements contained in the E2E header
Cyclic redundancy check (CRC)
The CRC is calculated by the sender for the contents of the safety critical communication data. The CRC protects against data corruption. The user is responsible for choosing an appropriate CRC polynomial with sufficient Hamming Distance to provide required error detection capability for a corresponding length of communication data. It is recommended to use a different CRC polynomial1 that the one used by the communication controller (if any) to provide redundancy. The receiver evaluates the CRC in the E2E header of the received communication frame to detect data corruption. A mismatch of the computed CRC value compared to the received CRC value indicates occurrence of data corruption.
1Hint: AUTOSAR Specification of SW-C End-to-End Communication Protection Library Release 4.3.1 recommends CRC polynomials to be used for various length of application data.
Counter
The Counter enables to detect faults such as loss of data, repetition of data. The sender for a given application data, inserts a counter value to the E2E header. The counter value is incremented for every transmission of the application data. The receiver evaluates the counter value in the E2E header of the received communication frame with an expected counter value. The following error scenarios can be detected
- Repetition of frame - The received counter value is the same as that of the previous counter value
- Loss of frame(s) - The received counter value is non –consecutive
The receiver upon successful evaluation of the received communication frame increments the corresponding current counter value.
Note: The user is responsible for implementing counter synchronization methods between the sender and receiver.
The application software can combine the counter value with a timer to detect delayed communication or block in the communication interface. Example: a timer (for example the system timer (STM)) can be configured to trigger a periodic check of the counter value of the associated application data. If the counter value does not change for a given time interval (for example within an FTTI), then delayed communication or block in communication is detected.
- ReqIF-WF.Type: Requirement

#### XEXA-FBFB-FDBA-ECHA: Controller Area Network XL interface (CANXL)
The CANXL module provides a communication interface according to the CiA 610-1 standard, supporting Classical CAN, CAN FD and CAN XL communication. It supports CAN XL data baudrates of up to 15 Mbits/s.
- IFX.Version: 1
- ReqIF-WF.Type: Information

##### FLZA-FBFB-FDEH-GIIF: Internal safety mechanisms
- IFX.Version: 1
- ReqIF-WF.Type: Information

###### XZDA-FDED-DHAH-GBCD: SM[HW]:CANXL:ENDINIT
- IFX.Version: 2
- ReqIF-WF.Type: Heading

###### XZDA-FDED-DHAH-GBCD_description: Description
The CANXL provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – CANXL (ascending offset address) in the User Manual.
- ReqIF-WF.Type: Information

###### XZDA-FDED-DHAH-GBCD_resetoperationalstate: Reset operational state
An application reset will set the configuration of this safety mechanism back to its default value.
- ReqIF-WF.Type: Information

###### XZDA-FDED-DHAH-GBCD_configurationandactivation: Configuration and activation
This safety mechanism is active after intentional configuration by application software through the PROTE registers.
- ReqIF-WF.Type: Requirement

###### XZDA-FDED-DHAH-GBCD_test: Test
This safety measure can be tested after the PROT owner has been configured:
Write access to a protected register by a master agent function that is not the PROT owner.
- ReqIF-WF.Type: Requirement

###### XZDA-FDED-DHAH-GBCD_reporting: Reporting
On detection of an access protection violation the CANXL will terminate the access with FPI error that is detected by the FPI, see SM[HW]:FPI:ERROR_HANDLING.
- ReqIF-WF.Type: Information

###### XZDA-FDED-DHAH-GBCD_recommendederrorreaction: Recommended error reaction
System integrator to select an appropriate safe reaction in the SMU.
- ReqIF-WF.Type: Information

###### YMPA-FDED-EHCA-AIHC: SM[HW]:CANXL:SAFETY_ENDINIT
- IFX.Version: 1
- ReqIF-WF.Type: Heading

###### YMPA-FDED-EHCA-AIHC_description: Description
The CANXL provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – CANXL (ascending offset address) in the User Manual.
- ReqIF-WF.Type: Information

###### YMPA-FDED-EHCA-AIHC_resetoperationalstate: Reset operational state
An application reset will set the configuration of this safety mechanism back to its default value.
- ReqIF-WF.Type: Information

###### YMPA-FDED-EHCA-AIHC_configurationandactivation: Configuration and activation
This safety mechanism is active after intentional configuration by application software through the PROTSE register.
- ReqIF-WF.Type: Requirement

###### YMPA-FDED-EHCA-AIHC_test: Test
This safety measure can be tested after the PROT owner has been configured:
Write access to a protected register by a master agent function that is not the PROT owner.
- ReqIF-WF.Type: Requirement

###### YMPA-FDED-EHCA-AIHC_reporting: Reporting
On detection of an access protection violation the CANXL will terminate the access with FPI error that is detected by the FPI, see SM[HW]:FPI:ERROR_HANDLING.
- ReqIF-WF.Type: Information

###### YMPA-FDED-EHCA-AIHC_recommendederrorreaction: Recommended error reaction
System integrator to select an appropriate safe reaction in the SMU.
- ReqIF-WF.Type: Information

###### SJWA-FDED-EHDB-DGAD: SM[HW]:CANXL:CFG_AS_AP
- IFX.Version: 2
- ReqIF-WF.Type: Heading

###### SJWA-FDED-EHDB-DGAD_description: Description
The CANXL checks if the access master agent function identifier is enabled for the type of access (read access and write access, configured through the CANXL ACCEN registers) to the selected register.
Unauthorized access attempts are blocked by this mechanism.
- ReqIF-WF.Type: Information

###### SJWA-FDED-EHDB-DGAD_resetoperationalstate: Reset operational state
An application reset will set the configuration of this safety mechanism back to its default value.
- ReqIF-WF.Type: Information

###### SJWA-FDED-EHDB-DGAD_configurationandactivation: Configuration and activation
This safety mechanism is active after intentional configuration by application software through the ACCEN registers.
- ReqIF-WF.Type: Requirement

###### SJWA-FDED-EHDB-DGAD_test: Test
This safety measure can be tested after the ACCEN has been configured:
Write access to a protected register by a master agent function that is not the ACCEN owner.
- ReqIF-WF.Type: Requirement

###### SJWA-FDED-EHDB-DGAD_reporting: Reporting
On detection of an access protection violation the CANXL will terminate the access with FPI error that is detected by the FPI, see SM[HW]:FPI:ERROR_HANDLING.
- ReqIF-WF.Type: Information

###### SJWA-FDED-EHDB-DGAD_recommendederrorreaction: Recommended error reaction
System integrator to select an appropriate safe reaction in the SMU.
- ReqIF-WF.Type: Information

###### CGPA-FDED-EHEG-CAHJ: SM[HW]:CANXL:SV_AP
- IFX.Version: 2
- ReqIF-WF.Type: Heading

###### CGPA-FDED-EHEG-CAHJ_description: Description
Critical module registers are implemented with a write access restriction that allows access only to masters with supervisor (SV) mode privilege.
Unauthorized access attempts are blocked by this mechanism.
For a list of the registers protected by SV, see tables Register overview – access mode glossary and Register overview – CANXL (ascending offset address) in the User Manual.
- ReqIF-WF.Type: Information

###### CGPA-FDED-EHEG-CAHJ_resetoperationalstate: Reset operational state
The safety mechanism is active after application reset.
- ReqIF-WF.Type: Information

###### CGPA-FDED-EHEG-CAHJ_configurationandactivation: Configuration and activation
N.A.
- ReqIF-WF.Type: Requirement

###### CGPA-FDED-EHEG-CAHJ_test: Test
This safety measure can be tested by an write access to a protected register by a master agent function without supervisor (SV) access rights.
- ReqIF-WF.Type: Requirement

###### CGPA-FDED-EHEG-CAHJ_reporting: Reporting
On detection of an access protection violation the CANXL will terminate the access with FPI error that is detected by the FPI, see SM[HW]:FPI:ERROR_HANDLING.
- ReqIF-WF.Type: Information

###### CGPA-FDED-EHEG-CAHJ_recommendederrorreaction: Recommended error reaction
System integrator to select an appropriate safe reaction in the SMU.
- ReqIF-WF.Type: Information

##### QIVA-FDBF-FDHB-DAHC: Alarms
CAN-XL alarms
| Alarm name | Safety mechanism | Alarm flag to be cleared in |
| --- | --- | --- |
| FPI error alarm | SM[HW]:CANXL:SV_AP SM[HW]:CANXL:CFG_AS_AP SM[HW]:CANXL:ENDINIT SM[HW]:CANXL:SAFETY_ENDINIT | SMU only |
| CANXL SRI Read Data EDC Error | SM[HW]:SRI:SRI_TRANSACTION_INTEGRITY | SMU only |
| CANXL SSH alarm | RAM ECC | CANXL and SMU |
- IFX.Version: 1
- ReqIF-WF.Type: Information

##### MCRA-FBFB-FDFB-ADII: External safety mechanisms
- IFX.Version: 1
- ReqIF-WF.Type: Information

###### KZIA-FDED-EHGH-BBEI: ESM[SW]:CANXL:SAFE_COMMUNICATION
- IFX.Version: 3
- ReqIF-WF.Type: Heading

###### KZIA-FDED-EHGH-BBEI_description: Description
Random hardware faults in the communication controller or in the communication interface can lead to corruption or loss of safety related data carried by a communication frame. In-order to detect the causes or effects of such communication faults, the application software has to implement safe End-to-End communication protecting the safety critical data.
The Safe End-to-End communication has to be implemented by application software of both the sender and the receiver of a communication frame. The sender appends an "E2E header" containing safety elements such as CRC or Counter to the communication data. The receivers evaluates the safety elements contained in the E2E header of the communication frame in order to detect faults. Figure below shows an example layout and construction of a communication frame protected by Safe End-to-End communication.
Safe end-to-end communication
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The following section describes the safety elements contained in the E2E header
Cyclic redundancy check (CRC)
The CRC is calculated by the sender for the contents of the safety critical communication data. The CRC protects against data corruption. The user is responsible for choosing an appropriate CRC polynomial with sufficient Hamming Distance to provide required error detection capability for a corresponding length of communication data. It is recommended to use a different CRC polynomial1 that the one used by the communication controller (if any) to provide redundancy. The receiver evaluates the CRC in the E2E header of the received communication frame to detect data corruption. A mismatch of the computed CRC value compared to the received CRC value indicates occurrence of data corruption.
1Hint: AUTOSAR Specification of SW-C End-to-End Communication Protection Library Release 4.3.1 recommends CRC polynomials to be used for various length of application data.
Counter
The Counter enables to detect faults such as loss of data, repetition of data. The sender for a given application data, inserts a counter value to the E2E header. The counter value is incremented for every transmission of the application data. The receiver evaluates the counter value in the E2E header of the received communication frame with an expected counter value. The following error scenarios can be detected
- Repetition of frame - The received counter value is the same as that of the previous counter value
- Loss of frame(s) - The received counter value is non –consecutive
The receiver upon successful evaluation of the received communication frame increments the corresponding current counter value.
Note: The user is responsible for implementing counter synchronization methods between the sender and receiver.
The application software can combine the counter value with a timer to detect delayed communication or block in the communication interface. Example: a timer (for example the system timer (STM)) can be configured to trigger a periodic check of the counter value of the associated application data. If the counter value does not change for a given time interval (for example within an FTTI), then delayed communication or block in communication is detected.
- ReqIF-WF.Type: Requirement

###### JAVA-FDED-EICB-DFFE: ESM[SW]:CANXL:ISR_MONITOR
- IFX.Version: 1
- ReqIF-WF.Type: Heading

###### JAVA-FDED-EICB-DFFE_description: Description
This ESM shall detect missing or unintended interrupts originating from the CANXL module.
Transmit/receive interrupts
The CANXL module signals to the application software that a message was received by triggering the interrupts Ni_FUNC_RAW.MH_RX_FQ(0-7)_IRQ and PRT_RX_EVT. Similarly, a transmitted message is signaled by triggering the interrupts Ni_FUNC_RAW.MH_TX_FQ(0-7)_IRQ and PRT_TX_EVT. To detect individual missing or unintended send or receive interrupts, the system integrator shall use the properties of the safe E2E communication (e.g. timestamp or frame counter). For example, a repeated receive frame counter value indicates that an unintended receive interrupt has occurred. Interrupts missing altogether are covered by the timeout mechanism of the safe E2E communication.
Upon detection of a missing or unintended interrupt, the application software shall trigger an appropriate reaction.
Other interrupts
Other interrupts originating from the CANXL module can be used if the system integrator wishes to do so. These are events mentioned in Ni_ERR_RAW SFR. Errors in the communication due to unintended or missing interrupts of this type are also covered by safe E2E communication.
Unused interrupts:
If the system integrator decides not to use certain interrupts, these shall be disabled in Ni_FUNC_ENA, Ni_ERR_ENA, Ni_SAFETY_ENA, Ni_MTI_ENA SFRs and in the interrupt router SRC register.
- ReqIF-WF.Type: Requirement

#### JUSA-EDCJ-DCED-IJHF: Clocking (CLOCK)
The clocking system is responsible for providing all clocks that are necessary for microcontroller operation. This is valid for all functional, test, and debug modes. It also provides clocks for external applications that can be selected from internal sources.
The clocking system is functionally divided into two major clock domains:
- System clock domain for clocks covering central processing units, interconnect and data transfers structures, non-volatile memories, timers, debug, trace and the core functions of the communication interfaces
- Peripheral clock domain for the protocol related parts of the communication interfaces and analog digital converters
Each domain has a master clock which is used to derive the related sub-clocks by programmable division and clock gating. System clocks are synchronous to each other, and peripheral clocks are asynchronous to each other and to the system clocks. Selected clocks can be routed to external outputs for debug, test, and further processing.
- IFX.Version: 1
- ReqIF-WF.Type: Information

##### GDQA-FAFE-IHDF-HDCJ: Internal safety mechanisms
- IFX.Version: 1
- ReqIF-WF.Type: Information

###### IBDA-EHHJ-FBJJ-IHDA: SM[HW]:CLOCK:ENDINIT
- IFX.Version: 1 1
- ReqIF-WF.Type: Heading

###### IBDA-EHHJ-FBJJ-IHDA_description: Description
The CLOCK provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – CLOCK (ascending offset address) in the User Manual.
- ReqIF-WF.Type: Information

###### IBDA-EHHJ-FBJJ-IHDA_resetoperationalstate: Reset operational state
An application reset will set the configuration of this safety mechanism back to its default value.
- ReqIF-WF.Type: Information

###### IBDA-EHHJ-FBJJ-IHDA_configurationandactivation: Configuration and activation
This safety mechanism is active after intentional configuration by application software through the PROTE register.
- ReqIF-WF.Type: Requirement

###### IBDA-EHHJ-FBJJ-IHDA_test: Test
This safety measure can be tested after the PROT owner has been configured:
Write access to a protected register by a master agent function that is not the PROT owner.
- ReqIF-WF.Type: Requirement

###### IBDA-EHHJ-FBJJ-IHDA_reporting: Reporting
On detection of an access protection violation the CLOCK will terminate the access with FPI error that is detected by the BCU, see SM[HW]:FPI:ERROR_HANDLING.
- ReqIF-WF.Type: Information

###### IBDA-EHHJ-FBJJ-IHDA_recommendederrorreaction: Recommended error reaction
System integrator to select an appropriate safe reaction in the SMU.
- ReqIF-WF.Type: Information

###### EPNA-EHHJ-FBJA-AJFE: SM[HW]:CLOCK:SAFETY_ENDINIT
- IFX.Version: 1 1
- ReqIF-WF.Type: Heading

###### EPNA-EHHJ-FBJA-AJFE_description: Description
The CLOCK provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – CLOCK (ascending offset address) in the User Manual.
- ReqIF-WF.Type: Information

###### EPNA-EHHJ-FBJA-AJFE_resetoperationalstate: Reset operational state
An application reset will set the configuration of this safety mechanism back to its default value.
- ReqIF-WF.Type: Information

###### EPNA-EHHJ-FBJA-AJFE_configurationandactivation: Configuration and activation
This safety mechanism is active after intentional configuration by application software through the PROTSE register.
- ReqIF-WF.Type: Requirement

###### EPNA-EHHJ-FBJA-AJFE_test: Test
This safety measure can be tested after the PROT owner has been configured:
Write access to a protected register by a master agent function that is not the PROT owner.
- ReqIF-WF.Type: Requirement

###### EPNA-EHHJ-FBJA-AJFE_reporting: Reporting
On detection of an access protection violation the CLOCK will terminate the access with FPI error that is detected by the BCU, see SM[HW]:FPI:ERROR_HANDLING.
- ReqIF-WF.Type: Information

###### EPNA-EHHJ-FBJA-AJFE_recommendederrorreaction: Recommended error reaction
System integrator to select an appropriate safe reaction in the SMU.
- ReqIF-WF.Type: Information

###### TAZA-EHHJ-FBJA-JDBG: SM[HW]:CLOCK:CFG_AS_AP
- IFX.Version: 1 1
- ReqIF-WF.Type: Heading

###### TAZA-EHHJ-FBJA-JDBG_description: Description
The CLOCK checks if the access master agent function identifier is enabled for the type of access (read access and write access, configured through the CLOCK ACCEN registers) to the selected register.
Unauthorized access attempts are blocked by this mechanism.
- ReqIF-WF.Type: Information

###### TAZA-EHHJ-FBJA-JDBG_resetoperationalstate: Reset operational state
An application reset will set the configuration of this safety mechanism back to its default value.
- ReqIF-WF.Type: Information

###### TAZA-EHHJ-FBJA-JDBG_configurationandactivation: Configuration and activation
This safety mechanism is active after intentional configuration by application software through the ACCENx registers.
- ReqIF-WF.Type: Requirement

###### TAZA-EHHJ-FBJA-JDBG_test: Test
This safety measure can be tested after the ACCENx has been configured:
Write access to a protected register by a master agent function that is not the ACCEN owner.
- ReqIF-WF.Type: Requirement

###### TAZA-EHHJ-FBJA-JDBG_reporting: Reporting
On detection of an access protection violation the CLOCK terminate the access with FPI error that is detected by the BCU, see SM[HW]:FPI:ERROR_HANDLING.
- ReqIF-WF.Type: Information

###### TAZA-EHHJ-FBJA-JDBG_recommendederrorreaction: Recommended error reaction
System integrator to select an appropriate safe reaction in the SMU.
- ReqIF-WF.Type: Information

###### IFDA-EHHJ-FBJJ-HACC: SM[HW]:CLOCK:SV_AP
- IFX.Version: 7 7
- ReqIF-WF.Type: Heading

###### IFDA-EHHJ-FBJJ-HACC_description: Description
Critical module registers are implemented with a write access restriction that allows access only to masters with supervisor (SV) mode privilege.
Unauthorized access attempts are blocked by this mechanism.
For a list of the registers protected by SV, see tables Register overview – access mode glossary and Register overview – CLOCK (ascending offset address) in the User Manual.
- ReqIF-WF.Type: Information

###### IFDA-EHHJ-FBJJ-HACC_resetoperationalstate: Reset operational state
The safety mechanism is active after application reset.
- ReqIF-WF.Type: Information

###### IFDA-EHHJ-FBJJ-HACC_configurationandactivation: Configuration and activation
N.A.
- ReqIF-WF.Type: Requirement

###### IFDA-EHHJ-FBJJ-HACC_test: Test
This safety measure can be tested by an write access to a protected register by a master agent function without supervisor (SV) access rights.
- ReqIF-WF.Type: Requirement

###### IFDA-EHHJ-FBJJ-HACC_reporting: Reporting
On detection of an access protection violation the CLOCK will terminate the access with FPI error that is detected by the BCU, see SM[HW]:FPI:ERROR_HANDLING.
- ReqIF-WF.Type: Information

###### IFDA-EHHJ-FBJJ-HACC_recommendederrorreaction: Recommended error reaction
System integrator to select an appropriate safe reaction in the SMU.
- ReqIF-WF.Type: Information

###### LELA-EHCA-EEGF-HFBJ: SM[HW]:CLOCK:REG_MONITOR
- IFX.Version: 1
- ReqIF-WF.Type: Heading

###### LELA-EHCA-EEGF-HFBJ_description: Description
The
safety mechanism detects transient and permanent faults in
sequential logic (Flip-Flops) of the clocking configuration
registers. It primarily works against transient faults in
configuration register using redundancy flip-flops. Permanent faults
can only be detected, if they lead to a mismatch in register values
after storage updates.
- ReqIF-WF.Type: Information

###### LELA-EHCA-EEGF-HFBJ_section2
Clocking system registers
with REG_MONITOR protection
are
listed in the following sorted by design
part:
- ReqIF-WF.Type: Information

###### LELA-EHCA-EEGF-HFBJ_mccumainregisterbank: MCCU (main register bank)
- OSCCON - Crystal oscillator control
- RAMPCON0 - Ramp oscillator control 0
- RAMPCON1 - Ramp oscillator control 1
- SYSPLLCON0 - System-PLL configuration 0
- SYSPLLCON1 - System-PLL configuration 1
- SYSPLLCON2 - System-PLL configuration 2
- PERPLLCON0 - Peripheral-PLL configuration 0
- PERPLLCON1 - Peripheral-PLL configuration 1
- PERPLLCON2 - Peripheral-PLL configuration 1
- CCUCON - Global clock control
- SYSCCUCON0 - System CCU clock control 0
- SYSCCUCON1 - System CCU clock control 1
- SYSCCUCONCS - System CCU cyber security clock control
- PERCCUCON0 - Peripheral CCU clock control 0
- PERCCUCON1 - Peripheral CCU clock control 1
- CCUMON - Global clock monitor
- OSCMON0 - EVR oscillator monitor
- OSCMON1 - Crystal oscillator monitor
- RAMPMON - Ramping oscillator monitor
- ReqIF-WF.Type: Information

###### LELA-EHCA-EEGF-HFBJ_pmsmainregisterbank: PMS (main register bank)
- HPOSCCON0 - HP Oscillator configuration 0
- HPOSCCON1 - HP Oscillator configuration 1
- ReqIF-WF.Type: Information

###### LELA-EHCA-EEGF-HFBJ_pcculocallymirroredregisters: PCCU (locally mirrored registers)
- PERPLLCON0 - Peripheral-PLL configuration 0
- PERPLLCON1 - Peripheral-PLL configuration 1
- PERPLLCON2 - Peripheral-PLL configuration 2
- ReqIF-WF.Type: Information

###### LELA-EHCA-EEGF-HFBJ_mplllocallymirroredregisters: MPLL (locally mirrored registers)
- SYSPLLCON1.K2DIV - K2- Divider configuration (System-PLL instance)
- PERPLLCON1.K2DIV - K2- Divider configuration (Peripheral-PLL instance)
- PERPLLCON1.K3DIV - K3- Divider configuration (Peripheral-PLL instance)
- PERPLLCON1.K4DIV - K4- Divider configuration (Peripheral-PLL instance)
- ReqIF-WF.Type: Information

###### LELA-EHCA-EEGF-HFBJ_ramposcillatorlocallymirroredregisters: Ramp oscillator (locally mirrored registers)
- RAMPCON0.UFL - Ramping oscillator upper frequency limit
- RAMPCON0.SIZE - Ramping oscillator frequency step size
- RAMPCON0.WAIT - Ramping oscillator wait time
- ReqIF-WF.Type: Information

###### LELA-EHCA-EEGF-HFBJ_resetoperationalstate: Reset operational state
This safety mechanism is reset according to the reset behavior of each of the registers above, as specified in the Register Overview - CLOCK table in the User Manual.
- ReqIF-WF.Type: Information

###### LELA-EHCA-EEGF-HFBJ_configurationandactivation: Configuration and activation
N.A.
- ReqIF-WF.Type: Requirement

###### LELA-EHCA-EEGF-HFBJ_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### LELA-EHCA-EEGF-HFBJ_reporting: Reporting
Upon detection of an error, an alarm will be reported to the SMU.
- ReqIF-WF.Type: Information

###### LELA-EHCA-EEGF-HFBJ_recommendederrorreaction: Recommended error reaction
System integrator to select appropriate safe reaction in SMU.
- ReqIF-WF.Type: Information

###### OSNA-EHCA-FDCE-DCCA: SM[HW]:CLOCK:XTAL_OSC_MONITOR
- IFX.Version: 20
- ReqIF-WF.Type: Heading

###### OSNA-EHCA-FDCE-DCCA_description: Description
The crystal oscillator monitor, also referred to as "oscillator watchdog", is responsible for checking the input clock of the PLLs with respect to the general presence of the input clock and its tolerable frequency range.
The monitor compares the input clock of the PLL against the internally generated and independent EVR oscillator clock. The EVR oscillator clock generates a timing reference window which is used to mark the start and stop of a counter to measure the number of input clock cycles during that window. The number of counted input clock cycles is compared with allowed tolerance values from a look-up table.
The look-up table reflects the allowed frequency range of the input clock and the comparator logic selects the respective entries from the table by applying a configured nominal input frequency. In case the measured clock cycles are below the lower limit, a "too-low" status is generated, if it is above the upper limit, a "too-high" status is generated respectively.
The monitor is capable of detecting if a potentially broken and defected crystal or ceramic resonator oscillates at half or doubled frequency. The monitor also detects if the input frequency is not present at all. This is sufficient to cover the faults of an external crystal.
The input cycle counter is running on the monitored clock f IN, the detector, comparator and reporting logic is running on the reference clock f BACK, the alarm is synchronized to f SPB.
The monitor is instantiated twice, that means one for System-PLL and one for Peripheral-PLL.
Crystal oscillator monitor
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- ReqIF-WF.Type: Information

###### OSNA-EHCA-FDCE-DCCA_resetoperationalstate: Reset operational state
This safety mechanism is reset by system reset.
- ReqIF-WF.Type: Information

###### OSNA-EHCA-FDCE-DCCA_configurationandactivation: Configuration and activation
The crystal oscillator monitor can be accessed by software through the following register:
- Crystal oscillator monitor register (OSCMON1)
The reference frequency of the monitor must be configured by setting the bit-field OSCMON1.OSCVAL. This is valid for both instances of the monitor as both share the same input clock, that means both monitor need to have the same reference frequency setting.
- ReqIF-WF.Type: Requirement

###### OSNA-EHCA-FDCE-DCCA_section4
The monitor can be activated and deactivated through the bit-fields OSCMON1.xMONEN for the Peripheral-PLL instance and the System-PLL instance as listed below.
Monitor configuration
and activation
| Monitor instance | Enable bit | Configuration |
| --- | --- | --- |
| System-PLL | SMONEN | OSCVAL |
| Peripheral-PLL | PMONEN | OSCVAL |
- ReqIF-WF.Type: Information

###### OSNA-EHCA-FDCE-DCCA_test: Test
The monitor logic can be tested through the bit-fields OSCMON1.xMONTST as listed below. The test enables minimize or maximize the input clock counter values that are checked against the reference value in the comparator. These manipulations in turn cause the comparator to report the respective status values, that means either too low or too high.
Monitor test
bits
| Monitor instance | Test bit |
| --- | --- |
| System-PLL | SMONTST |
| Peripheral-PLL | PMONTST |
- ReqIF-WF.Type: Requirement

###### OSNA-EHCA-FDCE-DCCA_reporting: Reporting
The crystal oscillator monitor status can be accessed by software through the following register:
- Crystal oscillator status register (OSCSTAT)
The monitor is capable of generating the status output values which reflect if the input frequency is too high or too low. If the input clock is not present at all, this is reflected by the "too low" status. If any of the below listed status bits has a rising edge, an alarm is generated and forwarded to the SMU.
Alarm
generation
| Monitor instance | Status bits | Alarm destination | Alarm name |
| --- | --- | --- | --- |
| System-PLL | SOWDS[1:0] | SMU | System-PLL crystal clock frequency out of range |
| Peripheral-PLL | POWDS[1:0] | SMU | Peripheral-PLL crystal clock frequency out of range |
- ReqIF-WF.Type: Information

###### OSNA-EHCA-FDCE-DCCA_recommendederrorreaction: Recommended error reaction
Only a reset higher or equal to a system reset would be able to solve a clock problem and resulting subsequent faults in the whole MCU. This reset can be generated internally or externally depending on the user’s settings. If the reset does not solve the problem, the root cause might be a permanent fault in the external crystal or resonator.
The system integrator shall select an appropriate safe reaction in the SMU or in response to the frequency out of range alarm.
- ReqIF-WF.Type: Information

###### YGRA-EHCA-FDFF-CCIE: SM[HW]:CLOCK:EVR_OSC_MONITOR
- IFX.Version: 19
- ReqIF-WF.Type: Heading

###### YGRA-EHCA-FDFF-CCIE_description: Description
The EVR oscillator monitor is responsible for checking the output clock f BACK of the EVR oscillator with respect to a programmable frequency range. It uses the output frequency of the System-PLL f PLL0 as diverse reference clock to generate a periodic trigger every 512 clock cycles. With every trigger, the monitor starts counting f BACK clock cycles and with the next trigger it evaluates the counted cycles. If the number of counted cycles is outside a window defined by programmable lower and upper thresholds, an alarm is generated. This check is periodically repeated, that means every 512 reference clock cycles.
EVR oscillator monitor
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- ReqIF-WF.Type: Information

###### YGRA-EHCA-FDFF-CCIE_resetoperationalstate: Reset operational state
This safety mechanism is reset by system reset.
- ReqIF-WF.Type: Information

###### YGRA-EHCA-FDFF-CCIE_configurationandactivation: Configuration and activation
The EVR oscillator monitor can be accessed by software through the following register:
- EVR oscillator monitor register (OSCMON0)
The upper and lower frequency thresholds of the monitor are configurable to adapt to the frequency of the reference clock. This is done by setting the bit-fields OSCMON0.LOTHR and OSCMON0.UPTHR.
The monitor can be activated and deactivated through the bit-field OSCMON0.MONEN.
Monitor
configuration and activation
| Monitor instance | Enable bit | Configuration |
| --- | --- | --- |
| EVR-oscillator | MONEN | LOTHR, UPTHR |
- ReqIF-WF.Type: Requirement

###### YGRA-EHCA-FDFF-CCIE_test: Test
The monitor logic can be tested through the bit-field OSCMON0.MONTST. The test enable forces a measurement result that is outside the allowed range. This causes the comparator to report an out of range alarm.
Monitor test
bits
| Monitor instance | Test bit |
| --- | --- |
| EVR-oscillator | MONTST |
- ReqIF-WF.Type: Requirement

###### YGRA-EHCA-FDFF-CCIE_reporting: Reporting
The monitor reports if the measured f BACK clock cycles are lower or higher than the defined thresholds. An alarm is generated and forwarded to the SMU.
Alarm
generation
| Monitor instance | Alarm destination | Alarm name |
| --- | --- | --- |
| EVR-oscillator | SMU | EVR oscillator clock frequency out of range |
- ReqIF-WF.Type: Information

###### YGRA-EHCA-FDFF-CCIE_recommendederrorreaction: Recommended error reaction
Only a reset higher or equal to a system reset would be able to solve a clock problem and resulting subsequent faults in the whole MCU. This reset can be generated internally or externally depending on the user’s settings.
The system integrator shall select an appropriate safe reaction in the SMU or in response to the frequency out of range alarm.
- ReqIF-WF.Type: Information

###### SCXA-EHCA-FDGB-AHJG: SM[HW]:CLOCK:ALIVE_MONITOR
- IFX.Version: 22
- ReqIF-WF.Type: Heading

###### SCXA-EHCA-FDGB-AHJG_description: Description
The alive oscillator monitor is responsible for checking a selected clock f XXX is alive, that means toggles with a minimum frequency. It uses a divers reference clock f REF to generate a periodic trigger every 512 clock cycles. The monitor checks that between two consecutive triggers the input clock f IN divided by 60 has toggled at least once. If this is not the case, an alarm is generated. This check is periodically repeated, that means every 512 reference clock cycles.
The alive monitor uses f BACK as reference for checking alive status of f PLL0, f PLL1, f PLL2, f PLL3and f PLLPPU. It uses f PLL0 as reference for checking alive status of f BACK and f RAMP.
The pre-divider is running on the monitored clock, the trigger generator and the toggle detector are running on the reference clock. The alarm is forwarded on the respective reference clock.
Alive monitor
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- ReqIF-WF.Type: Information

###### SCXA-EHCA-FDGB-AHJG_resetoperationalstate: Reset operational state
This safety mechanism is reset by system reset.
- ReqIF-WF.Type: Information

###### SCXA-EHCA-FDGB-AHJG_configurationandactivation: Configuration and activation
The alive monitor can be accessed by software through the following register:
- Global clock monitor register(CCUMON)
The monitor can be activated and deactivated through the bit-fields as listed below:
Monitor
configuration and activation
| Monitor instance | Enable bit |
| --- | --- |
| System-PLL, PLL0 | PLL0MONEN |
| System-PLL, PLLPPU | PLLPPUMONEN |
| Peripheral-PLL, PLL1 | PLL1MONEN |
| Peripheral-PLL, PLL2 | PLL2MONEN |
| Peripheral-PLL, PLL3 | PLL3MONEN |
| EVR-oscillator | BACKMONEN |
| Ramp-oscillator | RAMPMONEN |
- ReqIF-WF.Type: Requirement

###### SCXA-EHCA-FDGB-AHJG_test: Test
The monitor logic can be tested through the bit-fields located in CCUMON as listed below. The test enable signal masks off the input clock at the monitor. The masking causes the toggle detector to report the absence of the input clock and triggers the alarm.
Monitor test
bits
| Monitor instance | Enable bit |
| --- | --- |
| System-PLL, PLL0 | PLL0MONTST |
| System-PLL, PLLPPU | PLLPPUMONTST |
| Peripheral PLL, PLL1 | PLL1MONTST |
| Peripheral PLL, PLL2 | PLL2MONTST |
| Peripheral PLL, PLL3 | PLL3MONTST |
| EVR-oscillator | BACKMONTST |
| Ramp-oscillator | RAMPMONTST |
- ReqIF-WF.Type: Requirement

###### SCXA-EHCA-FDGB-AHJG_reporting: Reporting
Each monitor instance reports if the respective monitored clock f IN is alive. The related alarm is generated using the reference clock of the individual monitors and it is forwarded to the standby SMU or to the SMU as listed below:
Alarm
generation
| Monitor instance | Alarm destination | Alarm name |
| --- | --- | --- |
| System-PLL, PLL0, PLLPPU | Standby SMU | System-PLL clock alive error |
| Peripheral PLL, PLL1 | SMU | Peripheral-PLL clock alive error |
| Peripheral PLL, PLL2 | SMU | Peripheral-PLL clock alive error |
| Peripheral PLL, PLL3 | SMU | Peripheral-PLL clock alive error |
| EVR-oscillator | SMU | EVR oscillator clock alive error |
| Ramp-oscillator | SMU | Ramp oscillator clock alive error |
- ReqIF-WF.Type: Information

###### SCXA-EHCA-FDGB-AHJG_recommendederrorreaction: Recommended error reaction
Only a reset higher or equal to a system reset would be able to solve a clock problem and resulting subsequent faults in the whole MCU. This reset can be generated internally or externally depending on the user’s settings.
The system integrator shall select an appropriate safe reaction in the SMU or in response to the not-alive alarm.
- ReqIF-WF.Type: Information

###### TTAA-EHCA-FDFH-GDDJ: SM[HW]:CLOCK:PLL_LOL_MONITOR
- IFX.Version: 20
- ReqIF-WF.Type: Heading

###### TTAA-EHCA-FDFH-GDDJ_description: Description
A lock detection is integrated into the digital core of the PLL which calculates the phase error between f DCO/N and the reference Clock f REF. This phase error is used to indicate the lock condition. During operation the phase error is continuously monitored. As soon as the phase error exceeds a value of half a reference clock cycle, the lock status is set to zero. In addition, absence of the reference clock is also reported as out of lock. The transition of the lock signal from 1 to 0 is considered as loss of lock and triggers an alarm.
The monitor is used twice, for System-PLL and Peripheral-PLL.
PLL loss of lock monitor
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- ReqIF-WF.Type: Information

###### TTAA-EHCA-FDFH-GDDJ_resetoperationalstate: Reset operational state
The monitor is active after System Reset.
- ReqIF-WF.Type: Information

###### TTAA-EHCA-FDFH-GDDJ_configurationandactivation: Configuration and activation
The lock detector of the PLLs can be accessed by software through the following register:
- System-PLL configuration register 0 (SYSPLLCON0) for the System-PLL
- Peripheral-PLL configuration register 0 (PERPLLCON0) for the Peripheral-PLL
The loss of lock monitoring does not have any explicit configuration and enable. It gets active as soon as the related PLL is powered up. However, the lock detection can be reset and restarted through bit-field SYSPLLCON0.RESLD for the System-PLL and PERPLLCON0.RESLD for the Peripheral-PLL.
- ReqIF-WF.Type: Requirement

###### TTAA-EHCA-FDFH-GDDJ_test: Test
The monitor logic of the System-PLL can be tested through the nominal function bit-field .RESLD. The monitor logic of the Peripheral-PLL can be tested through the nominal function bit-field .RESLD. A reset of the lock detection causes the lock signal to be asserted low. This nominal function can be re-used to trigger a loss of lock alarm. A falling edge on the lock signal triggers the lock detector to report the "unlock" condition and the related alarms to be triggered.
Monitor test
bits
| Monitor instance | Test bit |
| --- | --- |
| System-PLL | RESLD |
| Peripheral-PLL | RESLD |
- ReqIF-WF.Type: Requirement

###### TTAA-EHCA-FDFH-GDDJ_reporting: Reporting
The lock status can access by software through the following registers:
- System-PLL status register (SYSPLLSTAT) for the System-PLL
- Peripheral-PLL status register (PERPLLSTAT) for the Peripheral-PLL
The loss of lock alarm is generated whenever a change from "lock" to "unlock" of the related PLL occurs. As the PLLs do not stop generating an output clock after a loss of lock event, the alarms will be forwarded to the SMU.
Alarm
generation
| Monitor instance | Alarm destination | Alarm name |
| --- | --- | --- |
| System-PLL | SMU | System-PLL loss of lock event |
| Peripheral-PLL | SMU | Peripheral-PLL loss of lock event |
- ReqIF-WF.Type: Information

###### TTAA-EHCA-FDFH-GDDJ_recommendederrorreaction: Recommended error reaction
Only a reset higher or equal to a system reset would be able to solve a clock problem and resulting subsequent faults in the whole MCU. This reset can be generated internally or externally depending on the user’s settings.
The system integrator shall select an appropriate safe reaction in the SMU or in response to the loss of lock alarm.
- ReqIF-WF.Type: Information

###### YWRA-EHCA-FEJJ-CBIH: SM[HW]:CLOCK:PLL_LCKSTP_MONITOR
Each monitor instance reports if the respective K-divider and K-pre-divider produce the configured clock ratio of f DCO/f PLL. For System-PLL monitoring, the alarm is forwarded to the standby SMU. For Peripheral-PLL monitoring, the alarm is forwarded to the SMU.
Alarm
generation
| Monitor instance | Alarm destination | Alarm name |
| --- | --- | --- |
| System-PLL, PLL0, PLLPPU | Standby SMU | System-PLL K-pre-divider K-divider error |
| Peripheral PLL, PLL1,PLL2,PLL3 | SMU | Peripheral-PLL K-pre-divider K-divider error |
- IFX.Version: 1
- ReqIF-WF.Type: Heading

###### YWRA-EHCA-FEJJ-CBIH_description: Description
The PLL lockstep monitor is used to safeguard the K-divider and K-pre-divider logic inside the generation function. The K-diver and K-pre-divider jointly define the output frequency of the PLL as follows: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
This monitor is composed of two configurable counters that are generating a toggle signal based on the DCO frequency f DCO and f PLL, respectively. Both counters are setup to produce identical toggle signals based on the least common multiple principle. A comparator checks if both toggle signals are identical and reports an error if not.
The toggle1 signal is generated by a counter running at fDCO that is basically the inverse divider of the PLL multiplied by 10. The toggle2 signal is generated by a counter running at fPLL that is always counting up to 10. The multiplication by 10 compensates the 0.1 resolution of the pre-divider.
PLL K-divider lockstep monitor
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The counters are setup as follows:
toggle signal
generation
| toggle1 (counter running at fDCO ) | toggle2 (counter running at fPLL ) |
| --- | --- |
| if (counter1<K×KPre×10) {counter1++;} else {toggle1 = !toggle1; counter1 = 1} | if (counter2<10) {counter 2++;} else {toggle2 = !toggle2; counter2=1;} |
Example:
- KPre = 1.6, K = 3
-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
-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
-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
- ReqIF-WF.Type: Information

###### YWRA-EHCA-FEJJ-CBIH_resetoperationalstate: Reset operational state
This safety mechanism is reset by system reset.
- ReqIF-WF.Type: Information

###### YWRA-EHCA-FEJJ-CBIH_configurationandactivation: Configuration and activation
The monitor can be accessed by software through the following register:
- Global clock monitor register(CCUMON)
The monitor can be activated and deactivated through the bit-fields as listed below:
Montor enable
bits
| Monitor instance | Enable bit |
| --- | --- |
| System-PLL, PLL0 | KDV0MONEN |
| System-PLL, PLLPPU | KDVPPUMONEN |
| Peripheral PLL, PLL1 | KDV1MONEN |
| Peripheral PLL, PLL2 | KDV2MONEN |
| Peripheral PLL, PLL3 | KDV3MONEN |
- ReqIF-WF.Type: Requirement

###### YWRA-EHCA-FEJJ-CBIH_test: Test
The monitor can be tested by software through the following register:
- Global clock monitor register(CCUMON)
The monitors can be tested through the bit-fields as listed below. The test enables manipulate the divider comparison which causes the monitors to report a misalignment of the divider outputs.
Monitor test
bits
| Monitor instance | Test bit |
| --- | --- |
| System-PLL, PLL0 | KDV0MONTST |
| System-PLL, PLLPPU | KDVPPUMONTST |
| Peripheral PLL, PLL1 | KDV1MONTST |
| Peripheral PLL, PLL2 | KDV2MONTST |
| Peripheral PLL, PLL3 | KDV3MONTST |
- ReqIF-WF.Type: Requirement

###### YWRA-EHCA-FEJJ-CBIH_reporting: Reporting
- ReqIF-WF.Type: Information

###### YWRA-EHCA-FEJJ-CBIH_recommendederrorreaction: Recommended error reaction
Only a reset higher or equal to a system reset would be able to solve a clock problem and resulting subsequent faults in the whole MCU. This reset can be generated internally or externally depending on the user’s settings.
The system integrator shall select an appropriate safe reaction in the SMU or in response to the K-divider error alarm.
- ReqIF-WF.Type: Information

###### GEBA-EHCA-FDHF-DDAC: SM[HW]:CLOCK:DIV_LCKSTP_MONITOR
- IFX.Version: 23
- ReqIF-WF.Type: Heading

###### GEBA-EHCA-FDHF-DDAC_description: Description
The divider lockstep monitor is used to safeguard the clock divider logic inside the distribution function. It compares the divided clock outputs with a second instance of the identical logic. This check is done every clock cycle of f sourcex with x = 0, 1, 2, 3, PPU. If the outputs differ for a single clock cycle, an alarm is generated.
Divider lockstep monitor
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- ReqIF-WF.Type: Information

###### GEBA-EHCA-FDHF-DDAC_resetoperationalstate: Reset operational state
This safety mechanism is reset by system reset.
- ReqIF-WF.Type: Information

###### GEBA-EHCA-FDHF-DDAC_configurationandactivation: Configuration and activation
The lockstep monitor can be accessed by software through the following register:
- Global clock monitor register(CCUMON)
The monitor can be activated and deactivated through the bit-fields as listed below:
Monitor enable
bits
| Monitor instance | Enable bit |
| --- | --- |
| System clock divider | SDIVMONEN |
| Peripheral clock divider and PPU clock divider | PDIVMONEN |
- ReqIF-WF.Type: Requirement

###### GEBA-EHCA-FDHF-DDAC_test: Test
The monitor logic can be tested through the bit-fields located in CCUMON as listed below. The test enable manipulates the divider comparison which causes the monitor to report a misalignment of the divider outputs.
Monitor test
bits
| Monitor instance | Test bit |
| --- | --- |
| System clock divider | SDIVTST |
| Peripheral clock divider and PPU clock divider | PDIVTST |
- ReqIF-WF.Type: Requirement

###### GEBA-EHCA-FDHF-DDAC_reporting: Reporting
Each monitor instance reports if the respective divider output and its lockstep divider counterpart have aligned outputs. The monitored divider, the monitoring lockstep divider and the comparator are running on the source clock f sourcex, that means f source0 for system clock dividers, f source1/2/3 for peripheral clock dividers and f sourceppu for PPU clock dividers. For system clock monitoring, the alarm is forwarded to the standby SMU. For peripheral clock and PPU clock checking the alarm is forwarded to the SMU.
Alarm
generation
| Monitor instance | Alarm destination | Alarm name |
| --- | --- | --- |
| System clock divider | Standby SMU | System clock divider error |
| Peripheral clock divider and PPU clock divider | SMU | Peripheral clock divider error |
- ReqIF-WF.Type: Information

###### GEBA-EHCA-FDHF-DDAC_recommendederrorreaction: Recommended error reaction
Only a reset higher or equal to a system reset would be able to solve a clock problem and resulting subsequent faults in the whole MCU. This reset can be generated internally or externally depending on the user’s settings.
The system integrator shall select an appropriate safe reaction in the SMU or in response to the divider error alarm.
- ReqIF-WF.Type: Information

###### HQWA-EHEA-BDDF-DADI: SM[HW]:CLOCK:RAMP_OSC_LOL_MONITOR
- IFX.Version: 1
- ReqIF-WF.Type: Heading

###### HQWA-EHEA-BDDF-DADI_description: Description
A lock detection is integrated into the digital core of the ramp oscillator which calculates the frequency error between f DCO and the target frequency f target. When the ramp sequencer is idle, the actual frequency is continuously measured and compared with the target frequency RAMCON.UFL. This check is continuously repeated and the lock status is reported to the MCCU. The transition of the lock signal from 1 to 0 while the ramp oscillator is not actively ramping as indicated by .SSTAT=Idle is considered as loss of lock and triggers an alarm.
Ramp oscillator loss of lock monitor
- ReqIF-WF.Type: Information

###### HQWA-EHEA-BDDF-DADI_resetoperationalstate: Reset operational state
The monitor is active after System Reset.
- ReqIF-WF.Type: Information

###### HQWA-EHEA-BDDF-DADI_configurationandactivation: Configuration and activation
The lock monitor can be configured and activated by software through the following register:
- Ramp oscillator monitor register (RAMPMON)
The loss of lock monitoring does not have any explicit configuration and enable. It gets active as soon as the related ramp oscillator is powered up. However, the lock detection can be reset and restarted through bit-field RAMPMON.RESFLLLD.
- ReqIF-WF.Type: Requirement

###### HQWA-EHEA-BDDF-DADI_test: Test
The monitor
logic can be tested through the nominal function bit-fieldRAMPMON.RESFLLLD. A
reset of the lock detection causes the lock signal to be asserted
low. This nominal function can be re-used to trigger a loss of lock
alarm. A falling edge on the lock signal triggers the lock detector
to report the "unlock" condition and the related alarm to be
triggered.
- ReqIF-WF.Type: Requirement

###### HQWA-EHEA-BDDF-DADI_reporting: Reporting
The loss of lock alarm is generated whenever a change from "lock" to "unlock" of the ramp oscillator occurs. The alarm will be forwarded to the SMU.
Alarm
generation
| Monitor instance | Alarm destination | Alarm name |
| --- | --- | --- |
| Ramp oscillator | SMU | Ramp oscillator loss of lock event |
- ReqIF-WF.Type: Information

###### HQWA-EHEA-BDDF-DADI_recommendederrorreaction: Recommended error reaction
Only a reset higher or equal to a system reset would be able to solve a clock problem and resulting subsequent faults in the whole MCU. This reset can be generated internally or externally depending on the user’s settings. In addition, it is possible to reset or re-initialize the ramp oscillator only.
The system integrator shall select an appropriate safe reaction in the SMU or in response to the loss of lock alarm.
- ReqIF-WF.Type: Information

##### MRXA-EHBJ-DHJD-GDAD: Alarms
CLOCK alarms
| Alarm name | Safety mechanism | Alarm flag to be cleared in |
| --- | --- | --- |
| EVR oscillator clock frequency out of range | SM[HW]:CLOCK:EVR_OSC_MONITOR | CLOCK and SMU |
| EVR oscillator clock alive error | SM[HW]:CLOCK:ALIVE_MONITOR | CLOCK and SMU |
| System-PLL crystal clock frequency out of range | SM[HW]:CLOCK:XTAL_OSC_MONITOR | CLOCK and SMU |
| System-PLL loss of lock event | SM[HW]:CLOCK:PLL_LOL_MONITOR | CLOCK and SMU |
| System-PLL clock alive error | SM[HW]:CLOCK:ALIVE_MONITOR | CLOCK and SMU |
| System-PLL K-pre-divider K-divider error | SM[HW]:CLOCK:PLL_LCKSTP_MONITOR | CLOCK and SMU |
| Ramp oscillator loss of lock event | SM[HW]:CLOCK:RAMP_OSC_LOL_MONITOR | CLOCK and SMU |
| Ramp oscillator clock alive error | SM[HW]:CLOCK:ALIVE_MONITOR | CLOCK and SMU |
| CCU safety flip-flop uncorrectable error | SM[HW]:CLOCK:CFG_MONITOR | CLOCK and SMU |
| Peripheral-PLL crystal clock frequency out of range | SM[HW]:CLOCK:EVR_OSC_MONITOR | CLOCK and SMU |
| Peripheral-PLL loss of lock event | SM[HW]:CLOCK:PLL_LOL_MONITOR | CLOCK and SMU |
| Peripheral-PLL clock alive error | SM[HW]:CLOCK:ALIVE_MONITOR | CLOCK and SMU |
| Peripheral-PLL K-pre-divider K-divider error | SM[HW]:CLOCK:PLL_LCKSTP_MONITOR | CLOCK and SMU |
| System clock divider error | SM[HW]:CLOCK:DIV_LCKSTP_MONITOR | CLOCK and SMU |
| Peripheral clock divider error | SM[HW]:CLOCK:DIV_LCKSTP_MONITOR | CLOCK and SMU |
| FPI error alarm | SM[HW]:CLOCK:SV_AP SM[HW]:CLOCK:CFG_AS_AP SM[HW]:CLOCK:ENDINIT SM[HW]:CLOCK:SAFETY_ENDINIT | SMU only |
- IFX.Version: 1
- ReqIF-WF.Type: Information

##### CROA-FAFE-IHDI-HJAD: External safety mechanisms
- IFX.Version: 1
- ReqIF-WF.Type: Information

###### YAEA-EHFD-BAHI-IBBH: ESM[SW]:CLOCK:CONFIG_READBACK
- IFX.Version: 10
- ReqIF-WF.Type: Heading

###### YAEA-EHFD-BAHI-IBBH_description: Description
The following registers of the clock configuration have to be read back after write. The read back values have to be compared with the written values. In case of any difference, the [Application Software] shall trigger an appropriate reaction.
- OSCCON - Crystal oscillator control
- RAMPCON0 - Ramp oscillator control 0
- SYSPLLCON0 - System-PLL configuration 0
- SYSPLLCON1 - System-PLL configuration 1
- SYSPLLCON2 - System-PLL configuration 2
- PERPLLCON0 - Peripheral-PLL configuration 0
- PERPLLCON1- Peripheral-PLL configuration 1
- PERPLLCON2- Peripheral-PLL configuration 2
- CCUCON - Global clock control
- SYSCCUCON0 - System CCU clock control 0
- SYSCCUCON1 - System CCU clock control 1
- SYSCCUCONCS - System CCU cyber security clock control
- PERCCUCON0 - Peripheral CCU clock control 0
- PERCCUCON1 - Peripheral CCU clock control 1
- CCUMON - Global clock monitor
- OSCMON0 - EVR oscillator monitor
- OSCMON1 - Crystal oscillator monitor
- RAMPMON - Ramping oscillator monitor
- ReqIF-WF.Type: Requirement

#### DSSA-EDDG-AHGD-JHDD: Central Processing Unit (CPU)
The TriCore™ 1.8 central processing unit (TC1.8 CPU) is a superscalar implementation of the version 1.8 of the TriCore™ architecture. TriCore™ is a 32-bit microcontroller-DSP architecture optimized for real-time embedded systems.
The TriCore™ instruction set architecture (ISA) combines the real-time capability of a microcontroller, the computational power of a Digital Signal Processor (DSP), and the high performance and features of a Reduced instruction set computer (RISC) load-store architecture, in a compact re-programmable core.
The ISA supports a uniform, 32-bit address space and memory-mapped Input/Output (IO). The architecture supports both 16-bit (reduced code space and low memory requirement) and 32-bit instruction formats. Real-time responsiveness is supported by low interrupt latency and fast-context-switching. The high performance architecture minimizes interrupt latency by avoiding long multi-cycle instructions and by providing a flexible hardware-supported interrupt scheme.
Version 1.8 of the TriCore™ architecture includes virtualization support and a double precision IEEE-754-2019 Floating-point unit.
Please note that TriCore™ architectural information is defined in the TriCore™ 1.8 architecture manual. Topics covered by that manual include:
- Architecture overview
- Programming model
- CPU registers
- Tasks and functions
- Interrupt handling
- Traps
- Memory protection system
- Temporal protection system
- Floating-point operations
- Debug
- Instruction set
- Virtualization
- IFX.Version: 1
- ReqIF-WF.Type: Information

##### AXVA-FAFF-JJJH-CHII: Internal safety mechanisms
- IFX.Version: 1
- ReqIF-WF.Type: Information

###### KKXA-EHDE-AHCJ-IFFF: SM[HW]:CPU:TRICORE_LOCKSTEP
- IFX.Version: 1
- ReqIF-WF.Type: Heading

###### KKXA-EHDE-AHCJ-IFFF_description: Description
The lockstep detects permanent and transient faults in the operation of a hardware element. Two symmetrical hardware modules perform duplicate operations in lockstep (or delayed by a fixed period) and the results are compared. Any mismatch results in an error condition.
A hardware based self-test detects latent faults in the lockstep and a software based test detects latent faults in the alarm.
The hardware element implements hardware redundancy by instancing two hardware modules known as the master and the checker, as well as a comparator. The two hardware modules use the same input data and perform the same function. During each clock cycle the comparator compares the master output against the checker output. If the comparator matches the master and checker output, the hardware element has performed the expected function. If there is a mismatch, the comparator has detected a fault in the operation of the hardware element and the comparator generates an alarm.
The lockstep is a variant of hardware redundancy that introduces a temporal separation between the master and checker:
- Every input to the checker is delayed by two clock cycles
- Every output from the master is delayed by two clock cycles
The comparator performs the output check two clock cycles after the master delivered the function output. The lockstep has no effect on the nominal operation.
Lockstep
- ReqIF-WF.Type: Information

###### KKXA-EHDE-AHCJ-IFFF_resetoperationalstate: Reset operational state
This safety mechanism is enabled after application reset.
- ReqIF-WF.Type: Information

###### KKXA-EHDE-AHCJ-IFFF_configurationandactivation: Configuration and activation
After cold reset lockstep is enabled by default. The LSEN bit in the LCLCON register may be cleared during the boot to disable lockstep mode. SMU lockstep fault reporting should be disabled when lockstep is disabled.
- ReqIF-WF.Type: Requirement

###### KKXA-EHDE-AHCJ-IFFF_test: Test
See SM[HW]:CPU:TRICORE_LOCKSTEP_SCC.
- ReqIF-WF.Type: Requirement

###### KKXA-EHDE-AHCJ-IFFF_reporting: Reporting
If this safety mechanism detects a fault, the CPU generates a CPU TriCore lockstep mismatch alarm.
- ReqIF-WF.Type: Information

###### KKXA-EHDE-AHCJ-IFFF_recommendederrorreaction: Recommended error reaction
System integrator to select appropriate safe reaction in SMU.
- ReqIF-WF.Type: Information

###### YXUA-EHDE-AHCF-CFGE: SM[HW]:CPU:TRICORE_LOCKSTEP_SCC
- IFX.Version: 1
- ReqIF-WF.Type: Heading

###### YXUA-EHDE-AHCF-CFGE_description: Description
The lockstep incorporates a hardware-based self-test. The self-test function sequentially injects faults into each comparator node. The lockstep detects that the fault was routed to the correct comparator node. If the fault was not routed to the correct comparator node or a real fault was detected, the lockstep generates an alarm.
The equivalent circuit for a lockstep comparator node with fault injection inputs is shown below. The self-test function injects faults into both the master and checker inputs of the critical outputs and qualified outputs.
Lockstep comparator node
The self-test function uses a free-running, binary counter using gray code number representation known as the input counter to calculate which comparator node will be tested in a given clock cycle. The self-test function will test every comparator node once every 8192 clock cycles. Alternate cycles of the self-test function will inject faults into either the master or checker side of a lockstep comparator node. A complete cycle of the self-test function will repeat every 16384 clock cycles. Injecting a fault into either side of a lockstep comparator node will cause the lockstep comparator node to fail unless a real fault occurs in the same clock cycle in which case the two faults will cancel out.
A second binary counter known as the monitor counter checks that the input counter has injected the fault into the intended lockstep comparator node. If the input counter and the monitor counter match the same comparator node and detect an injected fault, the lockstep will not generate an alarm. In the event a real fault has occurred the lockstep will generate an CPU TriCore lockstep mismatch alarm.
The following faults will be detected:
- An actual fault occurring at any of the master or checker inputs
- Includes the case of the actual fault coinciding with an injected fault
- A stuck at fault occurring at any of the comparator outputs
- A stuck at fault on signal x
- A stuck at fault on signal y
- A transient error occurring in the input counter
- A transient error occurring in the monitor counter
- ReqIF-WF.Type: Information

###### YXUA-EHDE-AHCF-CFGE_resetoperationalstate: Reset operational state
This safety mechanism is enabled after application reset.
- ReqIF-WF.Type: Information

###### YXUA-EHDE-AHCF-CFGE_configurationandactivation: Configuration and activation
The lockstep self-test function is enabled or disabled along with the lockstep function.
- ReqIF-WF.Type: Requirement

###### YXUA-EHDE-AHCF-CFGE_test: Test
The self-test function (triggered by setting LCLTEST.LCLT = 1) provides the application software with the ability to generate a lockstep alarm by injecting an error condition into the lockstep comparator.
The following faults will be detected:
- A stuck at fault on the alarm signal path
- ReqIF-WF.Type: Requirement

###### YXUA-EHDE-AHCF-CFGE_reporting: Reporting
If this safety mechanism detects a fault, the CPU generates an CPU TriCore lockstep mismatch alarm.
- ReqIF-WF.Type: Information

###### YXUA-EHDE-AHCF-CFGE_recommendederrorreaction: Recommended error reaction
System integrator to select appropriate safe reaction in SMU.
- ReqIF-WF.Type: Information

###### QEIA-EHDE-AHHH-DGJH: SM[HW]:CPU:CFI_LOCKSTEP
- IFX.Version: 1
- ReqIF-WF.Type: Heading

###### QEIA-EHDE-AHHH-DGJH_description: Description
The lockstep detects permanent and transient faults in the operation of a hardware element. Two symmetrical hardware modules perform duplicate operations in lockstep (or delayed by a fixed period) and the results are compared. Any mismatch results in an error condition.
A hardware based self-test detects latent faults in the lockstep and a software based test detects latent faults in the alarm.
The hardware element implements hardware redundancy by instancing two hardware modules known as the master and the checker, as well as a comparator. The two hardware modules use the same input data and perform the same function. During each clock cycle the comparator compares the master output against the checker output. If the comparator matches the master and checker output, the hardware element has performed the expected function. If there is a mismatch, the comparator has detected a fault in the operation of the hardware element and the comparator generates an alarm.
The lockstep is a variant of hardware redundancy that introduces a temporal separation between the master and checker:
- Every input to the checker is delayed by two clock cycles
- Every output from the master is delayed by two clock cycles
The comparator performs the output check two clock cycles after the master delivered the function output. The lockstep has no effect on the nominal operation.
Lockstep
- ReqIF-WF.Type: Information

###### QEIA-EHDE-AHHH-DGJH_resetoperationalstate: Reset operational state
This safety mechanism is enabled after application reset.
- ReqIF-WF.Type: Information

###### QEIA-EHDE-AHHH-DGJH_configurationandactivation: Configuration and activation
N.A.
- ReqIF-WF.Type: Requirement

###### QEIA-EHDE-AHHH-DGJH_test: Test
See SM[HW]:CPU:CFI_LOCKSTEP_SCC.
- ReqIF-WF.Type: Requirement

###### QEIA-EHDE-AHHH-DGJH_reporting: Reporting
If this safety mechanism detects a fault, the CFI generates a CFI lockstep mismatch alarm.
- ReqIF-WF.Type: Information

###### QEIA-EHDE-AHHH-DGJH_recommendederrorreaction: Recommended error reaction
System integrator to select appropriate safe reaction in SMU.
- ReqIF-WF.Type: Information

###### EYNA-EHDE-AHIA-CBDF: SM[HW]:CPU:CFI_LOCKSTEP_SCC
- IFX.Version: 1
- ReqIF-WF.Type: Heading

###### EYNA-EHDE-AHIA-CBDF_description: Description
The lockstep incorporates a hardware-based self-test. The self-test function sequentially injects faults into each comparator node. The lockstep detects that the fault was routed to the correct comparator node. If the fault was not routed to the correct comparator node or a real fault was detected, the lockstep generates an alarm.
The equivalent circuit for a lockstep comparator node with fault injection inputs is shown below. The self-test function injects faults into both the master and checker inputs of the critical outputs and qualified outputs.
Lockstep comparator node
The self-test function uses a free-running, binary counter using gray code number representation known as the input counter to calculate which comparator node will be tested in a given clock cycle. The self-test function will test every comparator node once every 8192 clock cycles. Alternate cycles of the self-test function will inject faults into either the master or checker side of a lockstep comparator node. A complete cycle of the self-test function will repeat every 16384 clock cycles. Injecting a fault into either side of a lockstep comparator node will cause the lockstep comparator node to fail unless a real fault occurs in the same clock cycle in which case the two faults will cancel out.
A second binary counter known as the monitor counter checks that the input counter has injected the fault into the intended lockstep comparator node. If the input counter and the monitor counter match the same comparator node and detect an injected fault, the lockstep will not generate an alarm. In the event a real fault has occurred the lockstep will generate an CFI lockstep mismatch alarm.
The following faults will be detected:
- An actual fault occurring at any of the master or checker inputs
- Includes the case of the actual fault coinciding with an injected fault
- A stuck at fault occurring at any of the comparator outputs
- A stuck at fault on signal x
- A stuck at fault on signal y
- A transient error occurring in the input counter
- A transient error occurring in the monitor counter
- ReqIF-WF.Type: Information

###### EYNA-EHDE-AHIA-CBDF_resetoperationalstate: Reset operational state
This safety mechanism is enabled after application reset.
- ReqIF-WF.Type: Information

###### EYNA-EHDE-AHIA-CBDF_configurationandactivation: Configuration and activation
N.A.
- ReqIF-WF.Type: Requirement

###### EYNA-EHDE-AHIA-CBDF_test: Test
The self-test function (triggered by setting CFI_LCLTEST.LCLT = 1) provides the application software with the ability to generate a lockstep alarm by injecting an error condition into the lockstep comparator.
The following faults will be detected:
- A stuck at fault on the alarm signal path
- ReqIF-WF.Type: Requirement

###### EYNA-EHDE-AHIA-CBDF_reporting: Reporting
If this safety mechanism detects a fault, the CFI generates an CFI lockstep mismatch alarm.
- ReqIF-WF.Type: Information

###### EYNA-EHDE-AHIA-CBDF_recommendederrorreaction: Recommended error reaction
System integrator to select appropriate safe reaction in SMU.
- ReqIF-WF.Type: Information

###### QNEA-EHDE-AIHH-AACF: SM[HW]:CPU:DLMU
If the CPU lockstep safety mechanism is disabled, the integrity of the data path between the SRI slave interface and the DLMU RAM is maintained. This applies for both read and write accesses.
Note: The path between the CPU (QM) and its local DLMU is expected to be blocked using the APU.
The safety mechanism consists of the following features:
- End-to-end SRI ECC integrity for reads to ensure data/address integrity of SRI accesses for remote masters reading from DLMU
- End-to-end SRI ECC integrity for writes to ensure data/address integrity of SRI accesses for remote masters writing to DLMU
- Write sequencing integrity to guaranty that all DLMU SRI write transactions reaching the target CPU slave interface result in a correct sequence of SRAM strobes on the DLMU RAM
- A redundant APU check to ensure freedom from interference from the local CPU
An error during a write transaction is not signaled to the master that initiated the transaction and incorrect data is written to the DLMU SRAM. This error case is detected at the target DLMU and an alarm is raised.
An error during a read transaction will not prevent the incorrect data to be sent to the remote master. This can therefore trigger other errors on the remote master due to incorrect data being propagated.
Note: When the CPU Lockstep safety mechanism is active, the integrity of the data path between SRI slave and the DLMU is ensured by the Lockstep safety mechanism.
- IFX.Version: 1
- ReqIF-WF.Type: Heading

###### QNEA-EHDE-AIHH-AACF_description: Description
- ReqIF-WF.Type: Information

###### QNEA-EHDE-AIHH-AACF_resetoperationalstate: Reset operational state
Always enabled.
- ReqIF-WF.Type: Information

###### QNEA-EHDE-AIHH-AACF_configurationandactivation: Configuration and activation
N.A.
- ReqIF-WF.Type: Requirement

###### QNEA-EHDE-AIHH-AACF_test: Test
This safety measure can be tested by a write access from CPUx targeting CPUy_DLMU with CPUx_SEGEN being configured for data master write data error insertion.
- ReqIF-WF.Type: Requirement

###### QNEA-EHDE-AIHH-AACF_reporting: Reporting
The CPU generates a CPU data side access EDC error alarm if any of the following events occur:
- The CPU detects a fault when checking the SRI address and control with the SRI address phase checksum
- The CPU detects a fault when checking the SRI write data with the SRI data phase checksum
- The CPU detects a fault when checking the CPU DLMU read data with the CPU DLMU ECC
- Includes a read-modify-write operation during a write access
- ReqIF-WF.Type: Information

###### QNEA-EHDE-AIHH-AACF_recommendederrorreaction: Recommended error reaction
System integrator to select appropriate safe reaction in SMU.
- ReqIF-WF.Type: Information

###### YOUA-EHDE-AIIF-GAGH: SM[HW]:CPU:CODE_MPU
- IFX.Version: 8
- ReqIF-WF.Type: Heading

###### YOUA-EHDE-AIIF-GAGH_description: Description
The CPU Code MPU protects user-specified memory ranges from unauthorized instruction fetches by the software running on the CPU. If the CPU Code MPU detects an unauthorized instruction fetch, the CPU Code MPU generates an exception.
A protection range is a contiguous part of the address space defined by a lower and upper address boundary for which access permissions are specified. A protection set is a complete set of protection region registers. The protection sets define instruction fetch permissions. The CPU Code MPU manages the changing of the protection set on a task context switch. Each task is assigned code execution ranges, for application code and shared code (libraries). Two levels of CPU Code MPU are implemented when support for virtualization is present in hardware and virtualization is enabled.
- ReqIF-WF.Type: Information

###### YOUA-EHDE-AIIF-GAGH_resetoperationalstate: Reset operational state
An application reset will set the configuration of this safety mechanism back to its default value (disabled).
- ReqIF-WF.Type: Information

###### YOUA-EHDE-AIIF-GAGH_configurationandactivation: Configuration and activation
The application software shall configure the protection ranges through the registers CPXE_y, CPRy_U, CPRy_L.
For level 1 MPU, 8 protection sets (CPXE_y) each of 16 protection ranges (CPRy_U and CPRy_L).
Level 1 MPU is enabled when CORECON.PROTEN == 1;
For level 2 MPU, 8 protection sets (HRHV_CPXE_y) each of 16 protection ranges (HRHV_CPRy_U, and HRHV_CPRy_L).
Level 2 MPU is always enabled when virtualization is present and enabled and a guest VM (VM1 to VM7) is running.
- ReqIF-WF.Type: Requirement

###### YOUA-EHDE-AIIF-GAGH_test: Test
N.A.
- ReqIF-WF.Type: Requirement

###### YOUA-EHDE-AIIF-GAGH_reporting: Reporting
An absence of permission in the L1 MPU raises:
- MPX, CLASS 1 TIN 4 trap
An absence of permission in the L2 MPU raises:
- L2_MPX, HVTRAP CLASS 3 TIN 1
- ReqIF-WF.Type: Information

###### YOUA-EHDE-AIIF-GAGH_recommendederrorreaction: Recommended error reaction
Both MPX and L2_MPX exception handlers are required to check whether the exception is legitimate (range swapping expected due to limited number of ranges) or unexpected (task or guest VM attempting an access to a restricted location). Afterward the exception handler shall trigger an appropriate safe reaction.
- ReqIF-WF.Type: Information

###### PSLA-EHDE-AIII-CJCF: SM[HW]:CPU:DATA_MPU
- IFX.Version: 1
- ReqIF-WF.Type: Heading

###### PSLA-EHDE-AIII-CJCF_description: Description
The CPU Data MPU protects user-specified memory ranges from unauthorized read and write accesses by the software running on the CPU. If the CPU Data MPU detects an unauthorized read or write, the CPU Data MPU generates an exception.
A protection range is a contiguous part of the address space defined by a lower and upper address boundary for which access permissions are specified. A protection set is a complete set of protection region registers. The protection sets define read and write memory access permissions. The CPU Data MPU manages the changing of the protection set on a task context switch. Each task is assigned data ranges for local data, constants (read only), global data and local stack. Two levels of CPU Data MPU are implemented when support for virtualization is present in hardware and virtualization is enabled.
- ReqIF-WF.Type: Information

###### PSLA-EHDE-AIII-CJCF_resetoperationalstate: Reset operational state
An application reset will set the configuration of this safety mechanism back to its default value (disabled).
- ReqIF-WF.Type: Information

###### PSLA-EHDE-AIII-CJCF_configurationandactivation: Configuration and activation
The application software shall configure the protection ranges through the registers DPRE_y, DPWE_y, DPRy_U, DPRy_L.
For level 1 MPU, 8 protection sets (DPRE_y and DPWE_y) each of 24 protection ranges (DPRy_U and DPRy_L).
Level 1 MPU is enabled when CORECON.PROTEN == 1;
For level 2 MPU, 8 protection sets (HRHV_DPRE_y and HRHV_DPWE_y) each of 24 protection ranges (HRHV_DPRy_U, and HRHV_DPRy_L).
Level 2 MPU is always enabled when virtualization is present and enabled and a guest VM (VM1 to VM7) is running.
- ReqIF-WF.Type: Requirement

###### PSLA-EHDE-AIII-CJCF_test: Test
N.A.
- ReqIF-WF.Type: Requirement

###### PSLA-EHDE-AIII-CJCF_reporting: Reporting
Violation of the L1 MPU raises:
- MPR, CLASS 1 TIN 2 trap
- MPW, CLASS 1 TIN 3 trap
- MPP, CLASS 1 TIN 5 trap
- MPN, CLASS 1 TIN 6 trap
Violation of the L2 MPU raises:
- L2_MPR, HVTRAP CLASS 2 - TIN 0
- L2_MPW, HVTRAP CLASS 2 - TIN 1
- ReqIF-WF.Type: Information

###### PSLA-EHDE-AIII-CJCF_recommendederrorreaction: Recommended error reaction
MPR, MPW, L2_MPR, and L2_MPW exception handlers are required to check whether the exception is legitimate (range swapping expected due to limited number of ranges) or unexpected (task or guest VM attempting an access to a restricted location). Afterward the exception handler shall trigger an appropriate safe reaction.
- ReqIF-WF.Type: Information

###### QKXA-FJGC-DCHC-FDJG: SM[HW]:CPU:ENDINIT
- IFX.Version: 1 1
- ReqIF-WF.Type: Heading

###### QKXA-FJGC-DCHC-FDJG_description: Description
The CPU provides PROT mechanisms (PROTSFRE, RSTE) that protect the configuration of the access protection mechanism (ACCEN). The ACCEN mechanism is based on the master agent function identifier. This supports freedom from interference of different SW tasks.
Unauthorized access attempts are blocked by this mechanism.
For a list of the registers protected by PROTSFRE and RSTE, see tables Register overview – access mode glossary and Register overview – CPU (ascending offset address) in the User Manual.
- ReqIF-WF.Type: Information

###### QKXA-FJGC-DCHC-FDJG_resetoperationalstate: Reset operational state
An application reset will set the configuration of this safety mechanism back to its default value.
- ReqIF-WF.Type: Information

###### QKXA-FJGC-DCHC-FDJG_configurationandactivation: Configuration and activation
This safety mechanism is active after intentional configuration by application software through the PROTSFRE and RSTE registers.
- ReqIF-WF.Type: Requirement

###### QKXA-FJGC-DCHC-FDJG_test: Test
This safety measure can be tested after the PROT owner has been configured:
Write access to a protected register by a master agent function that is not the PROT owner.
- ReqIF-WF.Type: Requirement

###### QKXA-FJGC-DCHC-FDJG_reporting: Reporting
On detection of an access protection violation the target CPU terminates the access and trigger an SMU alarm.
- ReqIF-WF.Type: Information

###### QKXA-FJGC-DCHC-FDJG_recommendederrorreaction: Recommended error reaction
System integrator to select an appropriate safe reaction in the SMU.
- ReqIF-WF.Type: Information

###### RUQA-EHHA-EECC-CCGI: SM[HW]:CPU:SAFETY_ENDINIT
- IFX.Version: 1 1
- ReqIF-WF.Type: Heading

###### RUQA-EHHA-EECC-CCGI_description: Description
The CPU provides PROT mechanisms (PROTSPRSE, PROTDLMUSE, PROTSFRSE, PROTSTMSE) that protect the configuration of the access protection mechanism (ACCEN). The ACCEN mechanism is based on the master agent function identifier. This supports freedom from interference of different SW tasks. Unauthorized access attempts are blocked by this mechanism.
For a list of the registers protected by PROTSPRSE, PROTDLMUSE, PROTSFRSE, PROTSTMSE see tables Register overview – access mode glossary and Register overview – CPU (ascending offset address) in the User Manual.
- ReqIF-WF.Type: Information

###### RUQA-EHHA-EECC-CCGI_resetoperationalstate: Reset operational state
An application reset will set the configuration of this safety mechanism back to its default value.
- ReqIF-WF.Type: Information

###### RUQA-EHHA-EECC-CCGI_configurationandactivation: Configuration and activation
This safety mechanism is active after intentional configuration by application software through the PROTSPRSE, PROTDLMUSE, PROTSFRSE and PROTSTMSE registers.
- ReqIF-WF.Type: Requirement

###### RUQA-EHHA-EECC-CCGI_test: Test
This safety measure can be tested after the PROT owner has been configured:
Write access to a protected register by a master agent function that is not the PROT owner.
- ReqIF-WF.Type: Requirement

###### RUQA-EHHA-EECC-CCGI_reporting: Reporting
On detection of an access protection violation the target CPU terminates the access and trigger an SMU alarm.
- ReqIF-WF.Type: Information

###### RUQA-EHHA-EECC-CCGI_recommendederrorreaction: Recommended error reaction
System integrator to select an appropriate safe reaction in the SMU.
- ReqIF-WF.Type: Information

###### XRVA-FJGE-IHFH-GGCD: SM[HW]:CPU:STARTUP_PROTECTION
System integrator to select an appropriate safe reaction in the SMU.
- IFX.Version: 1
- ReqIF-WF.Type: Heading

###### XRVA-FJGE-IHFH-GGCD_description: Description
After start-up, the startup software (SSW) automatically sets SMM_STCON.ST_PROT = 1 B for preventing unintentional changes by Application SW of start-up protected SFRs, which define MCU system characteristics. This monitors the STARTUP PROTECTION property on interconnect accesses to functional block configuration addresses (TriCore™ segment F H). The SFR configuration addresses for which this protection applies are defined in the register overview table of the device user manual (register requiring STP access mode).
- ReqIF-WF.Type: Information

###### XRVA-FJGE-IHFH-GGCD_resetoperationalstate: Reset operational state
This safety mechanism is always enabled during the Application SW.
- ReqIF-WF.Type: Information

###### XRVA-FJGE-IHFH-GGCD_configurationandactivation: Configuration and activation
N.A.
- ReqIF-WF.Type: Requirement

###### XRVA-FJGE-IHFH-GGCD_test: Test
This safety measure can be tested by an write access to a protected register by a master agent function while SMM_STCON.ST_PROT = 1 B.
- ReqIF-WF.Type: Requirement

###### XRVA-FJGE-IHFH-GGCD_reporting: Reporting
On detection of an access protection violation the target CPU terminates the access and trigger an SMU alarm.
- ReqIF-WF.Type: Information

###### XRVA-FJGE-IHFH-GGCD_recommendederrorreaction: Recommended error reaction
- ReqIF-WF.Type: Information

###### GYKA-EHHA-EECC-FFCJ: SM[HW]:CPU:SV_AP
- IFX.Version: 8 8
- ReqIF-WF.Type: Heading

###### GYKA-EHHA-EECC-FFCJ_description: Description
Critical module registers are implemented with a write access restriction that allows access only to masters with supervisor (SV) mode privilege.
Unauthorized access attempts are blocked by this mechanism.
For a list of the registers protected by SV, see tables Register overview – access mode glossary and Register overview – CPU (ascending offset address) in the User Manual.
- ReqIF-WF.Type: Information

###### GYKA-EHHA-EECC-FFCJ_resetoperationalstate: Reset operational state
The safety mechanism is active after application reset.
- ReqIF-WF.Type: Information

###### GYKA-EHHA-EECC-FFCJ_configurationandactivation: Configuration and activation
N.A.
- ReqIF-WF.Type: Requirement

###### GYKA-EHHA-EECC-FFCJ_test: Test
This safety measure can be tested by an write access to a protected register by a master agent function without supervisor (SV) access rights.
- ReqIF-WF.Type: Requirement

###### GYKA-EHHA-EECC-FFCJ_reporting: Reporting
On detection of an access protection violation the target CPU terminates the access with SRI error that is detected by the XBAR, see SM[HW]:SRI:ERROR_HANDLING.
- ReqIF-WF.Type: Information

###### GYKA-EHHA-EECC-FFCJ_recommendederrorreaction: Recommended error reaction
System integrator to select an appropriate safe reaction in the SMU.
- ReqIF-WF.Type: Information

###### IUPA-EHHA-EECC-FJII: SM[HW]:CPU:CFG_AS_AP
- IFX.Version: 1 1
- ReqIF-WF.Type: Heading

###### IUPA-EHHA-EECC-FJII_description: Description
The CPU checks if the access master agent function identifier is enabled for the type of access (read access and write access, configured through the CPU ACCEN registers) to the selected resource.
Unauthorized access attempts are blocked by this mechanism.
- ReqIF-WF.Type: Information

###### IUPA-EHHA-EECC-FJII_resetoperationalstate: Reset operational state
An application reset will set the configuration of this safety mechanism back to its default value.
- ReqIF-WF.Type: Information

###### IUPA-EHHA-EECC-FJII_configurationandactivation: Configuration and activation
This safety mechanism is active after intentional configuration by application software through the ACCENx registers.
- ReqIF-WF.Type: Requirement

###### IUPA-EHHA-EECC-FJII_test: Test
This safety measure can be tested after the ACCENx has been configured:
Write access to a protected register by a master agent function that is not the ACCEN owner.
- ReqIF-WF.Type: Requirement

###### IUPA-EHHA-EECC-FJII_reporting: Reporting
On detection of an access protection violation the target CPU terminates the access and trigger an SMU alarm. Read transactions are error terminated, which is detected by the XBAR, see SM[HW]:SRI:ERROR_HANDLING. For write transactions the protected resource is not modified.
- ReqIF-WF.Type: Information

###### IUPA-EHHA-EECC-FJII_recommendederrorreaction: Recommended error reaction
System integrator to select an appropriate safe reaction in the SMU.
- ReqIF-WF.Type: Information

###### SUEA-EHDE-AHAF-GBAA: SM[HW]:CPU:SWAP_MAP_SELECTION
- IFX.Version: 11
- ReqIF-WF.Type: Heading

###### SUEA-EHDE-AHAF-GBAA_description: Description
The system address map may be configured for linear address map, SOTA address map A or SOTA address map B. The CPU monitors the swap map selection.
- ReqIF-WF.Type: Information

###### SUEA-EHDE-AHAF-GBAA_resetoperationalstate: Reset operational state
This safety mechanism is always enabled.
- ReqIF-WF.Type: Information

###### SUEA-EHDE-AHAF-GBAA_configurationandactivation: Configuration and activation
N.A.
- ReqIF-WF.Type: Requirement

###### SUEA-EHDE-AHAF-GBAA_test: Test
N.A.
- ReqIF-WF.Type: Requirement

###### SUEA-EHDE-AHAF-GBAA_reporting: Reporting
If the CPU detects an illegal value in the swap map selection, the CPU generates a CPU swap map selection alarm.
- ReqIF-WF.Type: Information

###### SUEA-EHDE-AHAF-GBAA_recommendederrorreaction: Recommended error reaction
System integrator to select appropriate safe reaction in SMU.
- ReqIF-WF.Type: Information

###### DAYA-EHGD-FDIH-FHJG: SM[HW]:CPU:CFI_WAIT_STATE_PROTECTION
- IFX.Version: 7
- ReqIF-WF.Type: Heading

###### DAYA-EHGD-FDIH-FHJG_description: Description
The CPU uses an error correction code to detect a fault in the wait state configuration of the NVM to protect the NVM read timings. The wait state configuration is protected using an Error Detection Code (EDC) mechanism with single bit error and double bit error detection capabilities.
- ReqIF-WF.Type: Information

###### DAYA-EHGD-FDIH-FHJG_resetoperationalstate: Reset operational state
This safety mechanism is always enabled.
- ReqIF-WF.Type: Information

###### DAYA-EHGD-FDIH-FHJG_configurationandactivation: Configuration and activation
N.A.
- ReqIF-WF.Type: Requirement

###### DAYA-EHGD-FDIH-FHJG_test: Test
N.A.
- ReqIF-WF.Type: Requirement

###### DAYA-EHGD-FDIH-FHJG_reporting: Reporting
If the CPU detects a single or double bit error in the configuration of the program flash wait state, the CPU generates a CPU CFI wait state alarm.
- ReqIF-WF.Type: Information

###### DAYA-EHGD-FDIH-FHJG_recommendederrorreaction: Recommended error reaction
System integrator to select appropriate safe reaction in SMU.
- ReqIF-WF.Type: Information

###### VSPA-FBIG-BEFB-HDFA: SM[HW]:CPU:CFI_PFRWB_ADDRESS_MONITOR
- IFX.Version: 5
- ReqIF-WF.Type: Heading

###### VSPA-FBIG-BEFB-HDFA_description: Description
The address logic used in the interface between the CPU and the NVM is protected by a safety mechanism that checks that the returned data corresponds to the requested address. With each returned data, the PFRWB returns a copy of the requested address named safe_address. The CPU CFI HW uses this safe_address to compute a data phase ECC signature. If the CPU uses this data packet, another signature based on the requested address is computed by the CPU HW (code fetch interface or data read interface) and then both signatures are compared.
- ReqIF-WF.Type: Information

###### VSPA-FBIG-BEFB-HDFA_resetoperationalstate: Reset operational state
This safety mechanism is always enabled.
- ReqIF-WF.Type: Information

###### VSPA-FBIG-BEFB-HDFA_configurationandactivation: Configuration and activation
N.A.
- ReqIF-WF.Type: Requirement

###### VSPA-FBIG-BEFB-HDFA_test: Test
N.A.
- ReqIF-WF.Type: Requirement

###### VSPA-FBIG-BEFB-HDFA_reporting: Reporting
If the CPU uses this data packet and detects a mismatch in signatures, the CPU generates an alarm and an exception:
- For code fetch related packets, the CPU generates a PIE trap
- For data read related packets the CPU generates a DIE trap unless a previous DIE trap was already taken and DIETR.IED is not clear (See user manual for more details on DIE traps)
- ReqIF-WF.Type: Information

###### VSPA-FBIG-BEFB-HDFA_recommendederrorreaction: Recommended error reaction
System integrator to select appropriate safe reaction in SMU and implement appropriate safe reaction in the PIE and DIE exception handlers.
- ReqIF-WF.Type: Information

##### BCNA-EHBJ-CFJI-JDID: Alarms
CPU alarms
| Alarm name | Safety mechanism | Alarm flag to be cleared in |
| --- | --- | --- |
| CPU SOTA select redundancy error alarm | SM[HW]:CPU:SWAP_MAP_SLECTION | SMU only |
| CPU lockstep mismatch alarm | SM[HW]:CPU:TRICORE_LOCKSTEP SM[HW]:CPU:TRICORE_LOCKSTEP_SCC | SMU only |
| CPU data side access EDC error alarm | SM[HW]:CPU:DLMU SM[HW]:CPU:CFI_PFRWB_ADDRESS_MONITOR | SMU only |
| CPU instruction fetch EDC error alarm | SM[HW]:CPU:CFI_PFRWB_ADDRESS_MONITOR | SMU only |
| CPU CFI lockstep mismatch alarm | SM[HW]:CPU:CFI_LOCKSTEP SM[HW]:CPU:CFI_LOCKSTEP_SCC | SMU only |
| CPU CFI wait state error | SM[HW]:CPU:CFI_WAIT_STATE_PROTECTION | SMU only |
| CPU CFI access protection alarm | SM[HW]:CPU:STARTUP_PROTECTION SM[HW]:CPU:SV_AP SM[HW]:CPU:CFG_AS_AP SM[HW]:CPU:ENDINIT SM[HW]:CPU:SAFETY_ENDINIT | SMU only |
| CPU access protection alarm | SM[HW]:CPU:SV_AP SM[HW]:CPU:CFG_AS_AP SM[HW]:CPU:ENDINIT SM[HW]:CPU:SAFETY_ENDINIT | SMU only |
- IFX.Version: 1
- ReqIF-WF.Type: Information

##### XUKA-FAFF-JJAA-JECE: External safety mechanisms
- IFX.Version: 1
- ReqIF-WF.Type: Information

###### GZEA-EHDE-AIGA-AHAE: ESM[SW]:CPU:DATA_INTEGRITY
If the System Integrator wants to store data at memory locations that do not fulfill the assigned ASIL requirements (PSPR or DSPR of a disabled or non-lockstep CPU), the Application SW shall monitor the corruption of data stored in those locations caused by random hardware faults by using information redundancy. A possible implementation for such an information redundancy scheme could be as follows.
The data packet should be stored in with an expected checksum accumulated over all the data in the data packet. The calculation of the checksum should use a suitably robust algorithm (for example IEEE 802.3 standard or AUTOSAR CRC32P4 standard).
If the application software needs to use the data packet, the software should first copy the data packet to a memory supporting the ASIL requirements of the use case (for example PSPR, DSPR, DLMU or LMU). The software shall then store a calculated checksum for the copy of the data packet. After completion of the calculation, the software shall compare the calculated checksum and the expected checksum. If the calculated checksum and the expected checksum match, the software may use the data packet. If the calculated checksum and the expected checksum do not match, then the software must not use the data packet and initiate an appropriate system reaction.
Note: The comparison of the calculated checksum and the expected checksum must be performed on a lockstep CPU.
- IFX.Version: 9
- ReqIF-WF.Type: Heading

###### GZEA-EHDE-AIGA-AHAE_description: Description
- ReqIF-WF.Type: Requirement

#### ANXA-EDEA-CAHE-FGEE: Cyber Security Real-time Module (CSRM)
The CSRM functional block contains the four modules CSCU, PKC, RNG, and CSROM. The cyber security (CS) cluster is the combination of all modules and functions that in sum realize the cyber security functionality which was in previous device generations (AURIX™ TC2xx and TC3xx) realized by the hardware security module (HSM)
This CS cluster provides cryptographic services, a CPU dedicated to secured processing, and can also supervise the security of the application.
- IFX.Version: 1
- ReqIF-WF.Type: Information

##### ZHIA-FAFF-JGJG-BIBB: Internal safety mechanisms
- IFX.Version: 1
- ReqIF-WF.Type: Information

###### NBVA-FJGD-BIDF-CBGH: SM[HW]:CSRM:CFG_AS_AP
- IFX.Version: 4 4
- ReqIF-WF.Type: Heading

###### NBVA-FJGD-BIDF-CBGH_description: Description
The CSRM checks if the access master agent function identifier is enabled for the type of access (read access and write access, configured through the CSRM ACCEN registers) to the selected register.
Unauthorized access attempts are blocked by this mechanism.
- ReqIF-WF.Type: Information

###### NBVA-FJGD-BIDF-CBGH_resetoperationalstate: Reset operational state
An application reset will set the configuration of this safety mechanism back to its default value.
- ReqIF-WF.Type: Information

###### NBVA-FJGD-BIDF-CBGH_configurationandactivation: Configuration and activation
This safety mechanism is active after intentional configuration by application software through the ACCENx registers.
- ReqIF-WF.Type: Requirement

###### NBVA-FJGD-BIDF-CBGH_test: Test
This safety measure can be tested after the ACCENx has been configured:
Write access to a protected register by a master agent function that is not the ACCEN owner.
- ReqIF-WF.Type: Requirement

###### NBVA-FJGD-BIDF-CBGH_reporting: Reporting
On detection of an access protection violation the CSRM terminates the access with FPI error that is detected by the BCU, see SM[HW]:FPI:ERROR_HANDLING.
- ReqIF-WF.Type: Information

###### NBVA-FJGD-BIDF-CBGH_recommendederrorreaction: Recommended error reaction
System integrator to select an appropriate safe reaction in the SMU.
- ReqIF-WF.Type: Information

##### XIMA-EHBJ-CIGF-DHCD: Alarms
CSRM alarms
| Alarm name | Safety mechanism | Alarm flag to be cleared in |
| --- | --- | --- |
| SRI XBAR Bus Error Event Alarm | SM[HW]:CSRM:CFG_AS_AP | SMU only |
- IFX.Version: 1
- ReqIF-WF.Type: Information

##### STDA-FAFF-JGAA-BFGG: External safety mechanisms
- IFX.Version: 1
- ReqIF-WF.Type: Information

#### VIHA-EDCD-HBCF-GFEE: Cyber Security Satellite (CSS)
The Cyber Security Satellite (CSS) is a functional block that implements security functions. The CSS includes a SRI slave interface with a set of special function registers (SFRs).
- IFX.Version: 1
- ReqIF-WF.Type: Information

##### YGWA-FAFF-JGCH-EEGH: Internal safety mechanisms
- IFX.Version: 1
- ReqIF-WF.Type: Information

###### BKTA-EHBB-ACDF-HIID: SM[HW]:CSS:SAFE_MAC_COMP
- IFX.Version: 26
- ReqIF-WF.Type: Heading

###### BKTA-EHBB-ACDF-HIID_description: Description
Transient and permanent faults in the hash and MAC verification logic that could cause the acceptance of an incorrect message are detected. Upon detection an alarm is triggered. "Acceptance" of a message in this context means that the comparison of the supplied reference MAC or hash value in CHx_MAC_VALUEi with a MAC or hash value calculated from the message reports a match.
For the calculation of the MAC or hash from the message two modes are supported:
- Hardware MAC with hardware comparison: The MAC is calculated in the channel from data supplied to the channel
- Software MAC with hardware comparison: The MAC is calculated by CPUcs and supplied to CSS in register SWMAC_VALUEi for comparison
The following detection logic is implemented:
- The comparison itself is executed redundantly with two comparators
- The data paths and the address paths used to transfer the data, the calculated hash or MAC value and the reference hash or MAC value from their storage to the comparator is protected with EDC. Additionally the MAC size configured by the user and the one used by the comparator are compared
- All data stored in RAMs is protected with SECDED ECC
- The intrinsic attributes of hash and MAC algorithms (which can be regarded as pseudo-random number generators) ensure that incorrect input data or incorrect keys can only cause acceptance of wrong messages with the probability of 1 to 2^(length of compared hash or MAC value)
- Address mapped control and status registers for this functionality are protected by SFF, these are:
- Status register reporting the comparison result CHx_AUTHRES bit-fields RES and INVRES
- Configuration registers impacting this functionality are protected by SFF, see SM[HW]:CSS:REG_MONITOR
- The software evaluating the comparison result shall read both result flags RES and INVRES to detect inconsistency
- ReqIF-WF.Type: Information

###### BKTA-EHBB-ACDF-HIID_resetoperationalstate: Reset operational state
Above listed safety mechanisms are active from application reset on.
- ReqIF-WF.Type: Information

###### BKTA-EHBB-ACDF-HIID_configurationandactivation: Configuration and activation
Software shall configure the alarm handling using CHx_ALARM_CFG and CHx_ALARM_CFGSH to reflect the intended alarm handling architecture of the application. In general it is recommended that the alarm node configuration reflects ownership of the channel.
The alarm handling (enabling their processing and defining consequent actions) has to be configured in the SMU.
As described above the length of the comparison determines the error probability. Therefore, CHx_MACLEN.MACLEN shall be configured large enough. It is also advisable to ensure by according configuration of SWMAC_CTRL.MACSIZE or KEY_WRCMD.MACSIZE that no HASH or MAC comparisons are accepted with a length too short for safety (> 6 for ASIL-D) or security needs.
- ReqIF-WF.Type: Requirement

###### BKTA-EHBB-ACDF-HIID_test: Test
Testing of the alarm signals can be performed by the SMU_SAFE alarm testing function which is described with ESM[SW]:SMU:ALARM_SIGNAL_TEST. Additionally ESM[SW]:MCU:LBIST can be used to reduce the probability of remaining latent faults.
- ReqIF-WF.Type: Requirement

###### BKTA-EHBB-ACDF-HIID_reporting: Reporting
Alarm routing and its configuration are described in the section "Alarms" in the CSS chapter of the User Manual. To ensure that safety relevant alarms are routed to SMU_SAFE the channel has to be configured as described above using CHx_ALARM_CFG and CHx_ALARM_CFGSH to activate one of the "SAFETY_DOMAIN_ALARMi". This is supported by all channels except channel 0 which triggers exclusively "SECURED_DOMAIN_ALARM".
Faults detected by the SECDED ECC in CSS RAMs are reported by the VMT. These are not mapped to CSS alarms.
- ReqIF-WF.Type: Information

###### BKTA-EHBB-ACDF-HIID_recommendederrorreaction: Recommended error reaction
When software detects an inconsistent reporting of the comparison result in CHx_AUTHRES bit-fields RES and INVRES then it shall assume that the comparison failed.
Software can evaluate the type of alarm in CHx_ALARM_STAT and perform consequently a CSS channel reset or a complete device reset.
- ReqIF-WF.Type: Information

###### GCSA-EHBB-AECA-DEFJ: SM[HW]:CSS:REG_MONITOR
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- IFX.Version: 1
- ReqIF-WF.Type: Heading

###### GCSA-EHBB-AECA-DEFJ_description: Description
Transient faults in configuration registers that could cause the acceptance of an incorrect message are detected by SFF. These are:
- Configuration of the channel's alarm mapping in CHx_ALARM_CFGSH.ALMNODE and CHx_ALARM_CFG.ALMNODE
- Configuration of the size of the MAC value for comparison in CHx_CRYPT_CFG.MACLEN
- Configuration of the size of the hash value for comparison in CHx_HASH_CFG.HASHLEN
- Enable for dedicated/static AES engine mapping in CHx_CFG.FIXMAP
- Counter for the number of bytes of MAC value which have been written in CHx_MAC_STAT.MACBYTES
- ReqIF-WF.Type: Information

###### GCSA-EHBB-AECA-DEFJ_resetoperationalstate: Reset operational state
This safety mechanism is reset according to the reset behavior of each of the registers above, as specified in the Register Overview CSS table in the User Manual.
- ReqIF-WF.Type: Information

###### GCSA-EHBB-AECA-DEFJ_configurationandactivation: Configuration and activation
N.A.
- ReqIF-WF.Type: Requirement

###### GCSA-EHBB-AECA-DEFJ_test: Test
- ReqIF-WF.Type: Requirement

###### GCSA-EHBB-AECA-DEFJ_reporting: Reporting
Upon detection of an error, an alarm will be reported to the SMU.
The alarm name in the SMU alarm tables is "CSS SFF uncorrectable error alarm".
This is driven on CSS side by the global "SFF_ALARM". Details of alarm routing and its configuration are described in the section "Alarms" in the CSS chapter of the User Manual.
- ReqIF-WF.Type: Information

###### GCSA-EHBB-AECA-DEFJ_recommendederrorreaction: Recommended error reaction
System integrator to select appropriate safe reaction in SMU.
- ReqIF-WF.Type: Information

###### VXRA-FJGE-AIJI-IGFI: SM[HW]:CSS:SAFETY_ENDINIT
- IFX.Version: 1 1
- ReqIF-WF.Type: Heading

###### VXRA-FJGE-AIJI-IGFI_description: Description
The CSS provides PROT mechanisms (PROTCSE, CHx_PROTCSE) that protect the configuration of the access protection mechanism (ACCEN). The ACCEN mechanism is based on the master agent function identifier. This supports freedom from interference of different SW tasks.
Unauthorized access attempts are blocked by this mechanism.
For a list of the registers protected by PROTCSE and CHx_PROTCSE, see tables Register overview – access mode glossary and Register overview – CSS (ascending offset address) in the User Manual.
- ReqIF-WF.Type: Information

###### VXRA-FJGE-AIJI-IGFI_resetoperationalstate: Reset operational state
An application reset will set the configuration of this safety mechanism back to its default value.
- ReqIF-WF.Type: Information

###### VXRA-FJGE-AIJI-IGFI_configurationandactivation: Configuration and activation
This safety mechanism is active after intentional configuration by application software through the PROTCSE and CHx_PROTCSE registers.
- ReqIF-WF.Type: Requirement

###### VXRA-FJGE-AIJI-IGFI_test: Test
This safety measure can be tested after the PROT owner has been configured:
Write access to a protected register by a master agent function that is not the PROT owner.
- ReqIF-WF.Type: Requirement

###### VXRA-FJGE-AIJI-IGFI_reporting: Reporting
On detection of an access protection violation the CSS will terminate the access with SRI error that is detected by the XBAR, see SM[HW]:SRI:ERROR_HANDLING.
- ReqIF-WF.Type: Information

###### VXRA-FJGE-AIJI-IGFI_recommendederrorreaction: Recommended error reaction
System integrator to select an appropriate safe reaction in the SMU.
- ReqIF-WF.Type: Information

###### NQKA-FJGE-AIBE-ACBH: SM[HW]:CSS:SV_AP
- IFX.Version: 1 1
- ReqIF-WF.Type: Heading

###### NQKA-FJGE-AIBE-ACBH_description: Description
Critical module registers are implemented with a write access restriction that allows access only to masters with supervisor (SV) mode privilege.
Unauthorized access attempts are blocked by this mechanism.
For a list of the registers protected by SV see tables Register overview – access mode glossary and Register overview – CSS (ascending offset address) in the User Manual.
- ReqIF-WF.Type: Information

###### NQKA-FJGE-AIBE-ACBH_resetoperationalstate: Reset operational state
The safety mechanism is active after application reset.
- ReqIF-WF.Type: Information

###### NQKA-FJGE-AIBE-ACBH_configurationandactivation: Configuration and activation
N.A.
- ReqIF-WF.Type: Requirement

###### NQKA-FJGE-AIBE-ACBH_test: Test
This safety measure can be tested by an write access to a protected register by a master agent function without supervisor (SV) access rights.
- ReqIF-WF.Type: Requirement

###### NQKA-FJGE-AIBE-ACBH_reporting: Reporting
On detection of an access protection violation the CSS will terminate the access with SRI error that is detected by the XBAR, see SM[HW]:SRI:ERROR_HANDLING.
- ReqIF-WF.Type: Information

###### NQKA-FJGE-AIBE-ACBH_recommendederrorreaction: Recommended error reaction
System integrator to select an appropriate safe reaction in the SMU.
- ReqIF-WF.Type: Information

###### HUBA-FJGE-AIBA-JCII: SM[HW]:CSS:CFG_AS_AP
- IFX.Version: 1 1
- ReqIF-WF.Type: Heading

###### HUBA-FJGE-AIBA-JCII_description: Description
The CSS checks if the access master agent function identifier is enabled for the type of access (read access and write access, configured through the CSS ACCEN registers) to the selected register.
Unauthorized access attempts are blocked by this mechanism.
- ReqIF-WF.Type: Information

###### HUBA-FJGE-AIBA-JCII_resetoperationalstate: Reset operational state
An application reset will set the configuration of this safety mechanism back to its default value.
- ReqIF-WF.Type: Information

###### HUBA-FJGE-AIBA-JCII_configurationandactivation: Configuration and activation
This safety mechanism is active after intentional configuration by application software through the ACCENx registers.
- ReqIF-WF.Type: Requirement

###### HUBA-FJGE-AIBA-JCII_test: Test
This safety measure can be tested after the ACCENx has been configured:
Write access to a protected register by a master agent function that is not the ACCEN owner.
- ReqIF-WF.Type: Requirement

###### HUBA-FJGE-AIBA-JCII_reporting: Reporting
On detection of an access protection violation the CSS terminate the access with SRI error that is detected by the XBAR, see SM[HW]:SRI:ERROR_HANDLING.
- ReqIF-WF.Type: Information

###### HUBA-FJGE-AIBA-JCII_recommendederrorreaction: Recommended error reaction
System integrator to select an appropriate safe reaction in the SMU.
- ReqIF-WF.Type: Information

##### LPCA-EHBJ-DJJA-JCDA: Alarms
CSS alarms
| Alarm name | Safety mechanism | Alarm flag to be cleared in |
| --- | --- | --- |
| SFF_ALARM | SM[HW]:CSS:REG_MONITOR | SMU and set CSS_CHx_TRGRES.TRGRES |
| SECURED_DOMAIN_ALARM | SM[HW]:CSS:SAFE_MAC_COMP | SMU and set either CSS_CHx_ALARM_STATCLR.HWF or CSS_CHx_TRGRES.TRGRES |
| SAFETY_DOMAIN_ALARMi (where i=0...5) | SM[HW]:CSS:SAFE_MAC_COMP | SMU and set either CSS_CHx_ALARM_STATCLR.HWF or CSS_CHx_TRGRES.TRGRES |
| PHYSICAL_ERROR | SM[HW]:CSS:SAFE_MAC_COMP | SMU and set either CSS_CHx_ALARM_STATCLR.HWF or CSS_CHx_TRGRES.TRGRES |
| SRI XBAR Bus Error Event Alarm | SM[HW]:CSS:SV_AP SM[HW]:CSS:CFG_AS_AP SM[HW]:CSS:SAFETY_ENDINIT | SMU only and set CSS_CHx_ALARM_STATCLR.ILPROT |
- IFX.Version: 1
- ReqIF-WF.Type: Information

##### VHXA-FAFF-JGDA-JIDD: External safety mechanisms
- IFX.Version: 1
- ReqIF-WF.Type: Information

###### IUIA-EHBB-AEDG-FICI: ESM[SW]:CSS:FUNCTIONAL_MONITORING
- IFX.Version: 1
- ReqIF-WF.Type: Heading

###### IUIA-EHBB-AEDG-FICI_description: Description
For a safe implementation that prevents erroneous acceptance of wrong messages caused by random hardware faults (phrased differently: that prevents false positive verification of hashes or MACs) functional monitoring by application software is needed to detect errors caused by missing write data, wrong control register writes or transient faults in CSS internal logic.
Effectively application software shall ensure that the verification result is "fresh", that it reflects the current message. When starting a new hash or MAC verification operation the software shall check after writing the reference value to CHx_MAC_VALUEi that the bit-field DONE of CHx_AUTHRES is reset to 0 and the bit-fields RES and INVRES are reset to their "fail" values. After finishing the verification, the bit-field DONE must be 1. In addition it shall be checked that the bit field FAULT in the same register is 0 to ensure that no hardware fault occurred during operation.
Due to the nature of cryptographic algorithms, the probability of accepting a wrong message due to missing or incorrect keys or input data is sufficiently low. Therefore these failure modes are detected by monitoring the statistics of rejected messages, no further hardware measures are needed to cover these failure modes.
It is advisable that the monitoring software maintains error statistics available in CHx_AUTHFC to choose the best error reaction. Sporadically rejected messages (for example caused by a random fault in the message data) could be just ignored. Continuously rejected messages reported from one channel could be solved with a channel reset and reinstallation of keys and IVs. Messages rejected by several channels indicate that a common cause fault is present in HW or application SW and a full CSS reset by performing an Application Reset of the device is recommended.
- ReqIF-WF.Type: Requirement

###### XGDA-EHHE-GACA-IJAI: ESM[SW]:CSS:ISR_MONITOR
- IFX.Version: 13
- ReqIF-WF.Type: Heading

###### XGDA-EHHE-GACA-IJAI_description: Description
This ESM shall detect missing or unintended interrupts originating from the FB CSS in the context of its safety claim that with ASIL-D assurance the hash and MAC verification by CSS does not report wrong messages as correct.
Faults related to CSS interrupts (missing or unintended interrupts) cannot cause the acceptance of a wrong message by CSS because the cryptographic algorithms used for MAC and hash verification are chosen to be resistant even against intentional manipulation of data and therefore detect also accidental falsification of data. A hash or MAC verification by CSS is only successful when it has received data and reference hash or MAC that "fit" together.
Faults related to CSS interrupts change the stream of data which gets detected by the hash or MAC verification.
The only remaining risk to be covered by the application software in this ESM is the correct assignment of verification results to messages in case of missing or unintended interrupts. These are particularly these error cases:
- Evaluation of a verification result for a wrong message (verifies MAC "A" for message "A" but consumes unverified message B)
- Evaluation of a previous verification result (verifies successfully message "A" and due to missing interrupts does not perform the verification of message "B" but just reads the verification result of "A" again)
The safety measure ESM[SW]:CSS:ISR_MONITOR gives hints how the application can ensure that the consumed verification results are fresh and reflect the expected messages.
Derived from this the following handling is assumed for each type of interrupt:
- Input data FIFO event:
- Missing events of this kind can cause that too few data is copied into the input FIFO. As the message length has been pre-configured, CSS "knows" the expected amount of data and will not generate the MAC verification finished event. This case is assumed to be detected by the application for example by a time-out
- Unintended events of this kind can be detected by the application that supplies the data (because more data is requested than available). In case this is not handled by the application then additional data is copied into the CSS input FIFO. CSS discards this additional data for the ongoing message verification, which then delivers the correct result.
It can also happen that an unintended event of this kind causes data to be copied into the CSS input FIFO before sufficient space is available causing the input FIFO to overflow. This will abort the operation with an error and the DONE flag will not be set
- Output data FIFO event: This is not needed for message verification and therefore not monitored
- MAC generation/verification finished
- Missing events of this kind do not impact the outcome of the message verification but prevent reporting the availability of the result. This is assumed to be detected by the application for example by a time-out
- Unintended events of this kind are assumed to be detected by evaluating CHx_STAT_OP.MACVER before using the verification result. Only if MACVER is set the CSS has processed all data
- Error status
- Missing events of this kind are assumed to be detected by the application for example by a time-out because an error status event means that the MAC verification has not been performed and consequently there is no MAC generation/verification finished event
- Unintended events of this kind do not cause wrong interpretation of the verification result but can make CSS unusable. This is assumed to be resolved by executing a channel reset or device reset
In all these cases when faults are detected the application has to ensure that this does not cause wrong messages to be accepted.
- ReqIF-WF.Type: Requirement

#### YOFA-EEGA-DGEJ-CBGH: Debug
The On Chip Debug system (OCDS) includes all the capabilities required to access, configure and trigger debug functions. The functions are implemented in multiple sub-blocks that can be accessed from external debug tools as well as from internal running application software.
- IFX.Version: 1
- ReqIF-WF.Type: Information

##### HSDA-FAFF-JHCH-CEFF: Internal safety mechanisms
- IFX.Version: 1
- ReqIF-WF.Type: Information

###### WOJA-FBBJ-CAAE-GEEB: SM[HW]:DEBUG:FFI_CONTROL
- IFX.Version: 7
- ReqIF-WF.Type: Heading

###### WOJA-FBBJ-CAAE-GEEB_description: Description
For OSTATE.OEN, a safety flip-flop (SFF) is used which is capable of detecting transient and permanent faults. All other bits of the OSTATE register are gated by (OSTATE.OEN ORed IOSR.HOSTED). This gating blocks erroneous behavior when debug is disabled.
- ReqIF-WF.Type: Information

###### WOJA-FBBJ-CAAE-GEEB_resetoperationalstate: Reset operational state
The SFF is reset by .
- ReqIF-WF.Type: Information

###### WOJA-FBBJ-CAAE-GEEB_configurationandactivation: Configuration and activation
N.A.
- ReqIF-WF.Type: Requirement

###### WOJA-FBBJ-CAAE-GEEB_test: Test
The SFF used for OSTATE.OEN reuses the test mechanism of the REG_MONITOR SFFs. The following software routine shall be used to run the appropriate self-test:
- GCC_RMi_CTL.TEz
- Setting GCC_RMi_CTL.TEz to 1 starts a self-test on the OSTATE.OEN SFF (refer to the register monitor mapping tables in device specific part of user manual for the block instance i)
- The application software has to set this bit back to 0 at the end of the self-test
- GCC_RMi_EF.EFz
- GCC_RMi_EF.EFz is set to 1 whenever a fault is detected in the OSTATE.OEN SFF, regardless of the state of RMCTL.TE[i]
- The application software has to read this bit at the end of the self-test
- GCC_RMi_STS.STSz
- GCC_RMi_STS.STSz is set to 1 at the end of the SFF self-test sequence
- The application software has to read this bit to check the final status of self-test
Moreover self-test routine for multiple functional blocks can be run in parallel by setting multiple bits in GCC_RMi_CTL register.
- ReqIF-WF.Type: Requirement

###### WOJA-FBBJ-CAAE-GEEB_reporting: Reporting
If a transient or permanent fault is detected by the SFF, it is reported to the SMU on "OEN safety FF test fail".
- ReqIF-WF.Type: Information

###### WOJA-FBBJ-CAAE-GEEB_recommendederrorreaction: Recommended error reaction
The system integrator has to select an appropriate safe reaction in the SMU.
- ReqIF-WF.Type: Information

###### QURA-FBBB-JHJD-CICH: SM[HW]:DEBUG:CFG_AS_AP
- IFX.Version: 3
- ReqIF-WF.Type: Heading

###### QURA-FBBB-JHJD-CICH_description: Description
The CBS checks if the access master agent function identifier is enabled for the type of access (read access and write access, configured through the CBS ACCEN registers) to the selected register.
Unauthorized access attempts are blocked by this mechanism.
- ReqIF-WF.Type: Information

###### QURA-FBBB-JHJD-CICH_resetoperationalstate: Reset operational state
An application reset will set the configuration of this safety mechanism back to its default value.
- ReqIF-WF.Type: Information

###### QURA-FBBB-JHJD-CICH_configurationandactivation: Configuration and activation
This safety mechanism is active after intentional configuration by application software through the ACCENx registers.
- ReqIF-WF.Type: Requirement

###### QURA-FBBB-JHJD-CICH_test: Test
This safety measure can be tested after the ACCENx has been configured: Write access to a protected register by a master agent function that is not the ACCEN owner.
- ReqIF-WF.Type: Requirement

###### QURA-FBBB-JHJD-CICH_reporting: Reporting
On detection of an access protection violation the CBS terminates the access with FPI error that is detected by the BCU, see SM[HW]:FPI:ERROR_HANDLING.
- ReqIF-WF.Type: Information

###### QURA-FBBB-JHJD-CICH_recommendederrorreaction: Recommended error reaction
The system integrator has to select an appropriate safe reaction in the SMU.
- ReqIF-WF.Type: Information

##### ABRA-EHBA-BGAH-CIJD: Alarms
DEBUG alarms
| Alarm name | Safety mechanism | Alarm flag to be cleared in |
| --- | --- | --- |
| OEN safety FF test fail | SM[HW]:DEBUG:FFI_CONTROL | SMU only |
| FPI error alarm | SM[HW]:DEBUG:CFG_AS_AP | SMU only |
- IFX.Version: 1
- ReqIF-WF.Type: Information

##### VTYA-FAFF-JHDA-CDGE: External safety mechanisms
- IFX.Version: 1
- ReqIF-WF.Type: Information

#### GRIA-EDCJ-EGAF-CIJF: Flexible CRC Engine (FCE)
The FCE provides a parallel implementation of cyclic redundancy code (CRC) algorithms, implementing the IEEE 802.3 Ethernet CRC32, AUTOSAR CRC32P4, CCITT CRC16, and the SAE J1850 CRC8 polynomials. The FCE is targeted as a hardware acceleration engine for software applications or for operating system services that use CRC signatures.
- ReqIF-WF.Type: Information

##### RWAA-FAFF-FGHI-EDCF: Internal safety mechanisms
- IFX.Version: 1
- ReqIF-WF.Type: Information

###### FOXA-FBFC-EGAI-AHDI: SM[HW]:FCE:CFG_AS_AP
- IFX.Version: 3
- ReqIF-WF.Type: Heading

###### FOXA-FBFC-EGAI-AHDI_description: Description
The FCE checks if the access master agent function identifier is enabled for the type of access (read access and write access, configured through the FCE ACCEN registers) to the selected register.
Unauthorized access attempts are blocked by this mechanism.
- ReqIF-WF.Type: Information

###### FOXA-FBFC-EGAI-AHDI_resetoperationalstate: Reset operational state
An application reset will set the configuration of this safety mechanism back to its default value.
- ReqIF-WF.Type: Information

###### FOXA-FBFC-EGAI-AHDI_configurationandactivation: Configuration and activation
This safety mechanism is active after intentional configuration by application software through the ACCEN registers.
- ReqIF-WF.Type: Requirement

###### FOXA-FBFC-EGAI-AHDI_test: Test
This safety measure can be tested after the ACCEN has been configured:
Write access to a protected register by a master agent function that is not the ACCEN owner.
- ReqIF-WF.Type: Requirement

###### FOXA-FBFC-EGAI-AHDI_reporting: Reporting
On detection of an access protection violation the FCE will terminate the access with FPI error that is detected by the BCU, see SM[HW]:FPI:ERROR_HANDLING.
- ReqIF-WF.Type: Information

###### FOXA-FBFC-EGAI-AHDI_recommendederrorreaction: Recommended error reaction
System integrator to select an appropriate safe reaction in the SMU.
- ReqIF-WF.Type: Information

##### EPKA-EHBA-BFBA-DAAH: Alarms
FCE alarms
| Alarm name | Safety mechanism | Alarm flag to be cleared in |
| --- | --- | --- |
| FPI error alarm | SM[HW]:FCE:CFG_AS_AP | SMU only |
- IFX.Version: 1
- ReqIF-WF.Type: Information

##### JQHA-FAFF-FGIJ-HAFJ: External safety mechanisms
This section is not applicable for the module being described.
- IFX.Version: 1
- ReqIF-WF.Type: Information

#### ZUYA-EDEA-DBAH-HBCJ: Firmware
Firmware consists of software components that are stored in ROM. It performs start-up of the device after power-on or reset, and supports additional features such as handling debug access to the device, bootstrap loading of executable code, controlled shut-down after reset request, and power-friendly debug monitor routines for example.
- IFX.Version: 1
- ReqIF-WF.Type: Information

##### SGFA-FAFF-FHHI-JDGA: Internal safety mechanisms
This section is not applicable for the module being described.
- IFX.Version: 1
- ReqIF-WF.Type: Information

##### TPYA-EHBA-BHAB-JFFE: Alarms
No safety alarms in FIRMWARE.
- IFX.Version: 1
- ReqIF-WF.Type: Information

##### URQA-FAFF-FHIJ-EHGF: External safety mechanisms
This section is not applicable for the module being described.
- IFX.Version: 1
- ReqIF-WF.Type: Information

#### JVIA-EDBI-IEIB-BJGF: Flexible Peripheral Interconnect (FPI)
The system on chip (SoC) communication is mainly based on three interconnect protocols: SRI, FPI, and LLI.
The Flexible peripheral interconnect (FPI) is multi-master interconnect, 32-bit data width, based on FPI interconnect protocol. The FPI connects the high speed peripherals, such as the TC1.8 CPU´s and DMA modules to the medium and low bandwidth functional blocks.
- IFX.Version: 1
- ReqIF-WF.Type: Information

##### DKEA-FAFF-FICG-JGCD: Internal safety mechanisms
- IFX.Version: 1
- ReqIF-WF.Type: Information

###### MPUA-EHGD-FIJB-JHAG: SM[HW]:FPI:ERROR_HANDLING
- IFX.Version: 1
- ReqIF-WF.Type: Heading

###### MPUA-EHGD-FIJB-JHAG_description: Description
When a master agent access on an FPI interconnect is terminated with an FPI error the related FPI control unit (BCU) captures information about the related transaction and signals an alarm to the SMU.
An FPI transaction can be terminated by addressed slave agent:
- If the type of access is not supported by the slave agent for the access address
- If the access results in an access protection violation in the slave agent
An FPI transaction can be terminated by the BCU:
- If a data phase of the access exceeds the configured maximum number of wait states (FPI timeout)
An FPI transaction is terminated by the FPI interconnect:
- For an access with a address that is not assigned to a slave agent (reserved address)
Note: Capturing of CS related transaction information is controlled by the CSRM system.
- ReqIF-WF.Type: Information

###### MPUA-EHGD-FIJB-JHAG_resetoperationalstate: Reset operational state
The safety mechanism is active from application reset on.
- ReqIF-WF.Type: Information

###### MPUA-EHGD-FIJB-JHAG_configurationandactivation: Configuration and activation
N.A.
- ReqIF-WF.Type: Requirement

###### MPUA-EHGD-FIJB-JHAG_test: Test
This safety measure can be tested by an access to a reserved system address.
- ReqIF-WF.Type: Requirement

###### MPUA-EHGD-FIJB-JHAG_reporting: Reporting
On detection of an FPI error the BCU signals an Alarm_NCS to the SMU_SAFE or an Alarm_CS alarm to the SMU_CS, depending if the access terminated with FPI error was security critical.
- ReqIF-WF.Type: Information

###### MPUA-EHGD-FIJB-JHAG_recommendederrorreaction: Recommended error reaction
System integrator to select appropriate safe reaction in SMU.
- ReqIF-WF.Type: Information

###### AHOA-EHGD-GJAH-AEBD: SM[HW]:FPI:TRANSACTION_INTEGRITY
- IFX.Version: 1
- ReqIF-WF.Type: Heading

###### AHOA-EHGD-GJAH-AEBD_description: Description
The FPI interconnect provides EDC mechanisms to ensure transaction integrity.
An FPI master agent permanently EDC encodes the FPI request signals that are permanently EDC checked by the FPI control unit (BCU). If the FPI interconnect detects an EDC error, an alarm is signaled.
An active FPI master agent in the address phase EDC encodes the address and control signals that are then checked at the target FPI slave agent. If the FPI slave agent detects an error, an alarm is signaled.
An active FPI master agent in the data phase EDC encodes the FPI data phase control signals and the transmitted write data which are checked by the active FPI slave agent. If the FPI slave agent detects an error, an alarm is signaled.
An active FPI slave agent in the data phase EDC encodes the FPI data phase control signals and the transmitted read data which are checked by the active FPI master agent . If the FPI master agent detects an error, an alarm is signaled.
The FPI interconnect permanently checks the number of active FPI master and active slaves agents:
- If more than one master or more than one slave agent is active at the same time, an alarm is signaled
- If a master agent that was granted by the Interconnect for access does not become active, an alarm is signaled
- If a master agent access is not taken by a slave agent the access is terminated with FPI error and an alarm is signaled
- ReqIF-WF.Type: Information

###### AHOA-EHGD-GJAH-AEBD_resetoperationalstate: Reset operational state
The safety mechanism is active from application reset on.
- ReqIF-WF.Type: Information

###### AHOA-EHGD-GJAH-AEBD_configurationactivation: Configuration & activation
N.A.
- ReqIF-WF.Type: Requirement

###### AHOA-EHGD-GJAH-AEBD_test: Test
The Application SW shall detect for the FPI master agents and the FPI slave agents connected to an FPI interconnect if the EDC alarm signal lines from agents to the BCU are working correctly. The Application SW shall execute the test of the alarm signals from FPI agent to the respective BCU, at least once per driving cycle.
The test can be implemented through the BCU error generation function (register FEGEN). A detailed description can be found in the FPI User´s Manual chapter.
The FPI master and slave agents for which an FPI EDC alarm signal test must be performed are defined in the Alarm status control registers (ALSTATx) of the respective BCU.
On detection of the injected FPI EDC error through the SMU alarm and the set in the related BCU ALSTAT register, the respective bit in the BCU ALSTAT register has to be cleared and the alarm overflow bit in the BCU ALCTRL to be checked to ensure that no real error happened in parallel.
In case the BCU ALCTRL overflow bit (ALOV) is set, a device reset is advisable.
- ReqIF-WF.Type: Requirement

###### AHOA-EHGD-GJAH-AEBD_reporting: Reporting
On detection of an FPI EDC error the BCU signals an Alarm_CS to the SMU_SAFE.
- ReqIF-WF.Type: Information

###### AHOA-EHGD-GJAH-AEBD_recommendederrorreaction: Recommended error reaction
It is recommended to perform an application reset.
- ReqIF-WF.Type: Information

###### OVFA-EHGD-GBBG-CHBH: SM[HW]:FPI:ADDRESS_MAP_MONITORING
- IFX.Version: 9
- ReqIF-WF.Type: Heading

###### OVFA-EHGD-GBBG-CHBH_description: Description
An active FPI slave agent
- Checks that the received address is used functionally in the module
- On detection of an access to a reserved address the FPI slave agent signals either directly an alarm to the SMU or it terminates the access with FPI error which the BCU detects and signals an alarm to the SMU
The FPI interconnect
- checks that the address of an access is assigned to an FPI slave agent
- If a master agent access is not taken by a slave agent the access is terminated with FPI error and an alarm is signaled
- ReqIF-WF.Type: Information

###### OVFA-EHGD-GBBG-CHBH_resetoperationalstate: Reset operational state
The safety mechanism is active from application reset on.
- ReqIF-WF.Type: Information

###### OVFA-EHGD-GBBG-CHBH_configurationactivation: Configuration & activation
N.A.
- ReqIF-WF.Type: Requirement

###### OVFA-EHGD-GBBG-CHBH_test: Test
This safety measure can be tested by an access to an address that is not related to a module.
- ReqIF-WF.Type: Requirement

###### OVFA-EHGD-GBBG-CHBH_reporting: Reporting
On detection of an FPI error the BCU signals an Alarm_NCS to SMU_SAFEor Alarm_CS to SMU_CS depending if the cause of the error was security critical.
- ReqIF-WF.Type: Information

###### OVFA-EHGD-GBBG-CHBH_recommendederrorreaction: Recommended error reaction
System integrator to select appropriate safe reaction in SMU.
- ReqIF-WF.Type: Information

###### QROA-EHGD-GBDF-JJFF: SM[HW]:FPI:ENDINIT
- IFX.Version: 1 1
- ReqIF-WF.Type: Heading

###### QROA-EHGD-GBDF-JJFF_description: Description
The FPI provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – FPI (ascending offset address) in the User Manual.
- ReqIF-WF.Type: Information

###### QROA-EHGD-GBDF-JJFF_resetoperationalstate: Reset operational state
An application reset will set the configuration of this safety mechanism back to its default value.
- ReqIF-WF.Type: Information

###### QROA-EHGD-GBDF-JJFF_configurationandactivation: Configuration and activation
This safety mechanism is active after intentional configuration by application software through the PROTE register.
- ReqIF-WF.Type: Requirement

###### QROA-EHGD-GBDF-JJFF_test: Test
This safety measure can be tested after the PROT owner has been configured:
Write access to a protected register by a master agent function that is not the PROT owner.
- ReqIF-WF.Type: Requirement

###### QROA-EHGD-GBDF-JJFF_reporting: Reporting
On detection of an access protection violation the FPI will terminate the access with FPI error that is detected by the BCU, see SM[HW]:FPI:ERROR_HANDLING.
- ReqIF-WF.Type: Information

###### QROA-EHGD-GBDF-JJFF_recommendederrorreaction: Recommended error reaction
System integrator to select an appropriate safe reaction in the SMU.
- ReqIF-WF.Type: Information

###### NREA-EHGD-GBEJ-IEJG: SM[HW]:FPI:SAFETY_ENDINIT
- IFX.Version: 13 13
- ReqIF-WF.Type: Heading

###### NREA-EHGD-GBEJ-IEJG_description: Description
The FPI provides a unique PROT mechanism (PROTSE) that protects the configuration of the access protection mechanism (ACCEN). The ACCEN mechanism is based on the master agent function identifier. This supports freedom from interference of different SW tasks.
Unauthorized access attempts are blocked by this mechanism.
For the list of registers protected by PROTSE, see tables Register overview – access mode glossary and Register overview – FPI (ascending offset address) in the User Manual.
- ReqIF-WF.Type: Information

###### NREA-EHGD-GBEJ-IEJG_resetoperationalstate: Reset operational state
An application reset will set the configuration of this safety mechanism back to its default value.
- ReqIF-WF.Type: Information

###### NREA-EHGD-GBEJ-IEJG_configurationandactivation: Configuration and activation
This safety mechanism is active after intentional configuration by application software through the PROTSE register.
- ReqIF-WF.Type: Requirement

###### NREA-EHGD-GBEJ-IEJG_test: Test
This safety measure can be tested after the PROT owner has been configured:
Write access to a protected register by a master agent function that is not the PROT owner.
- ReqIF-WF.Type: Requirement

###### NREA-EHGD-GBEJ-IEJG_reporting: Reporting
On detection of an access protection violation the FPI will terminate the access with FPI error that is detected by the BCU, see SM[HW]:FPI:ERROR_HANDLING.
- ReqIF-WF.Type: Information

###### NREA-EHGD-GBEJ-IEJG_recommendederrorreaction: Recommended error reaction
System integrator to select an appropriate safe reaction in the SMU.
- ReqIF-WF.Type: Information

###### WNMA-EHGD-FIAJ-HHHE: SM[HW]:FPI:SV_AP
- IFX.Version: 9 9
- ReqIF-WF.Type: Heading

###### WNMA-EHGD-FIAJ-HHHE_description: Description
Critical module registers are implemented with a write access restriction that allows access only to masters with supervisor (SV) mode privilege.
Unauthorized access attempts are blocked by this mechanism.
For a list of the registers protected by SV, see tables Register overview – access mode glossary and Register overview – FPI (ascending offset address) in the User Manual.
- ReqIF-WF.Type: Information

###### WNMA-EHGD-FIAJ-HHHE_resetoperationalstate: Reset operational state
The safety mechanism is active after application reset.
- ReqIF-WF.Type: Information

###### WNMA-EHGD-FIAJ-HHHE_configurationandactivation: Configuration and activation
N.A.
- ReqIF-WF.Type: Requirement

###### WNMA-EHGD-FIAJ-HHHE_test: Test
This safety measure can be tested by an write access to a protected register by a master agent function without supervisor (SV) access rights.
- ReqIF-WF.Type: Requirement

###### WNMA-EHGD-FIAJ-HHHE_reporting: Reporting
On detection of an access protection violation the FPI will terminate the access with FPI error that is detected by the BCU, see SM[HW]:FPI:ERROR_HANDLING.
- ReqIF-WF.Type: Information

###### WNMA-EHGD-FIAJ-HHHE_recommendederrorreaction: Recommended error reaction
System integrator to select an appropriate safe reaction in the SMU.
- ReqIF-WF.Type: Information

###### JMXA-EHGD-GBEG-CAHA: SM[HW]:FPI:CFG_AS_AP
- IFX.Version: 1 1
- ReqIF-WF.Type: Heading

###### JMXA-EHGD-GBEG-CAHA_description: Description
The FPI checks if the access master agent function identifier is enabled for the type of access (read access and write access, configured through the FPI ACCEN registers) to the selected register.
Unauthorized access attempts are blocked by this mechanism.
- ReqIF-WF.Type: Information

###### JMXA-EHGD-GBEG-CAHA_resetoperationalstate: Reset operational state
An application reset will set the configuration of this safety mechanism back to its default value.
- ReqIF-WF.Type: Information

###### JMXA-EHGD-GBEG-CAHA_configurationandactivation: Configuration and activation
This safety mechanism is active after intentional configuration by application software through the ACCENx registers.
- ReqIF-WF.Type: Requirement

###### JMXA-EHGD-GBEG-CAHA_test: Test
This safety measure can be tested after the ACCENx has been configured:
Write access to a protected register by a master agent function that is not the ACCEN owner.
- ReqIF-WF.Type: Requirement

###### JMXA-EHGD-GBEG-CAHA_reporting: Reporting
On detection of an access protection violation the FPI terminate the access with FPI error that is detected by the BCU, see SM[HW]:FPI:ERROR_HANDLING.
- ReqIF-WF.Type: Information

###### JMXA-EHGD-GBEG-CAHA_recommendederrorreaction: Recommended error reaction
System integrator to select an appropriate safe reaction in the SMU.
- ReqIF-WF.Type: Information

##### UJQA-EHBJ-CGED-FIHD: Alarms
FPI alarms
| Alarm name | Safety mechanism | Alarm flag to be cleared in |
| --- | --- | --- |
| FPI EDC error alarm (Alarm_NCS) | SM[HW]:FPI:FPI_TRANSACTION_INTEGRITY | SMU and BCU |
| FPI error alarm (Alarm_NCS) | SM[HW]:FPI:ADDRESS_MAP_MONITORING SM[HW]:FPI:ERROR_HANDLING SM[HW]:FPI:SV_AP SM[HW]:FPI:CFG_AS_AP SM[HW]:FPI:ENDINIT SM[HW]:FPI:SAFETY_ENDINIT | SMU only |
| FPI error alarm (Alarm_CS) | SM[HW]:FPI:ADDRESS_MAP_MONITORING SM[HW]:FPI:ERROR_HANDLING SM[HW]:FPI:SV_AP SM[HW]:FPI:CFG_AS_AP SM[HW]:FPI:ENDINIT SM[HW]:FPI:SAFETY_ENDINIT | SMU only |
- IFX.Version: 1
- ReqIF-WF.Type: Information

##### FTCA-FAFF-FICH-FCJG: External safety mechanisms
- IFX.Version: 1
- ReqIF-WF.Type: Information

###### BNWA-EHGD-GBFH-BBAI: ESM[SW]:FPI:CONFIG_READBACK
- IFX.Version: 1
- ReqIF-WF.Type: Heading

###### BNWA-EHGD-GBFH-BBAI_description: Description
Software can detect missing writes to configuration registers by reading them back after configuration. Single occurrence of missing write transactions can be handled by repeating the missing write. Frequent errors of this type can have various reasons from disturbed operating conditional to permanent hardware faults. Generally a device reset is advisable.
The following registers of the FPI BCU configuration have to be read back after configuration:
- PROTE
- PROTSE
- ACCEN registers
- PRIOH
- PRIOL
- RRCTRL
- ALCTRL
- QOSICTRL
- QOSMCTRL
- ReqIF-WF.Type: Requirement

#### YUPA-EEFH-JDBG-IJBE: General Purpose Timer (GPT12)
The General Purpose Timer Unit blocks GPT1 and GPT2 have very flexible multifunctional timer structures which may be used for timing, event counting, pulse width measurement, pulse generation, frequency multiplication and other purposes. They incorporate five 16-bit timers that are grouped into the two timer blocks GPT1 and GPT2. Each timer in each block may operate independently in a number of different modes such as Gated Timer or Counter Mode or may be concatenated with another timer of the same block. Each block has alternate input and output functions and specific interrupts (service requests) associated with it. Input signals can be selected from several sources by register PISEL. The GPT12 module is clocked with clock f GPT.
- IFX.Version: 1
- ReqIF-WF.Type: Information

##### EGBA-FAFF-GAJH-CJAJ: Internal safety mechanisms
- IFX.Version: 1
- ReqIF-WF.Type: Information

###### EZIA-EHHJ-ECHB-FDJF: SM[HW]:GPT12:ENDINIT
- IFX.Version: 8 8
- ReqIF-WF.Type: Heading

###### EZIA-EHHJ-ECHB-FDJF_description: Description
The GPT12 provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – GPT12 (ascending offset address) in the User Manual.
- ReqIF-WF.Type: Information

###### EZIA-EHHJ-ECHB-FDJF_resetoperationalstate: Reset operational state
An application reset will set the configuration of this safety mechanism back to its default value.
- ReqIF-WF.Type: Information

###### EZIA-EHHJ-ECHB-FDJF_configurationandactivation: Configuration and activation
This safety mechanism is active after intentional configuration by application software through the PROTE register.
- ReqIF-WF.Type: Requirement

###### EZIA-EHHJ-ECHB-FDJF_test: Test
This safety measure can be tested after the PROT owner has been configured:
Write access to a protected register by a master agent function that is not the PROT owner.
- ReqIF-WF.Type: Requirement

###### EZIA-EHHJ-ECHB-FDJF_reporting: Reporting
On detection of an access protection violation the GPT12 will terminate the access with FPI error that is detected by the BCU, see SM[HW]:FPI:ERROR_HANDLING.
- ReqIF-WF.Type: Information

###### EZIA-EHHJ-ECHB-FDJF_recommendederrorreaction: Recommended error reaction
System integrator to select an appropriate safe reaction in the SMU.
- ReqIF-WF.Type: Information

###### QVCA-EHHJ-ECHB-GEGJ: SM[HW]:GPT12:SAFETY_ENDINIT
- IFX.Version: 7 7
- ReqIF-WF.Type: Heading

###### QVCA-EHHJ-ECHB-GEGJ_description: Description
The GPT12 provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – GPT12 (ascending offset address) in the User Manual.
- ReqIF-WF.Type: Information

###### QVCA-EHHJ-ECHB-GEGJ_resetoperationalstate: Reset operational state
An application reset will set the configuration of this safety mechanism back to its default value.
- ReqIF-WF.Type: Information

###### QVCA-EHHJ-ECHB-GEGJ_configurationandactivation: Configuration and activation
This safety mechanism is active after intentional configuration by application software through the PROTSE register.
- ReqIF-WF.Type: Requirement

###### QVCA-EHHJ-ECHB-GEGJ_test: Test
This safety measure can be tested after the PROT owner has been configured:
Write access to a protected register by a master agent function that is not the PROT owner.
- ReqIF-WF.Type: Requirement

###### QVCA-EHHJ-ECHB-GEGJ_reporting: Reporting
On detection of an access protection violation the GPT12 will terminate the access with FPI error that is detected by the BCU, see SM[HW]:FPI:ERROR_HANDLING.
- ReqIF-WF.Type: Information

###### QVCA-EHHJ-ECHB-GEGJ_recommendederrorreaction: Recommended error reaction
System integrator to select an appropriate safe reaction in the SMU.
- ReqIF-WF.Type: Information

###### SAJA-EHHJ-ECHB-FIHJ: SM[HW]:GPT12:CFG_AS_AP
- IFX.Version: 5 5
- ReqIF-WF.Type: Heading

###### SAJA-EHHJ-ECHB-FIHJ_description: Description
The GPT12 checks if the access master agent function identifier is enabled for the type of access (read access and write access, configured through the GPT12 ACCEN registers) to the selected register.
Unauthorized access attempts are blocked by this mechanism.
- ReqIF-WF.Type: Information

###### SAJA-EHHJ-ECHB-FIHJ_resetoperationalstate: Reset operational state
An application reset will set the configuration of this safety mechanism back to its default value.
- ReqIF-WF.Type: Information

###### SAJA-EHHJ-ECHB-FIHJ_configurationandactivation: Configuration and activation
This safety mechanism is active after intentional configuration by application software through the ACCENx registers.
- ReqIF-WF.Type: Requirement

###### SAJA-EHHJ-ECHB-FIHJ_test: Test
This safety measure can be tested after the ACCENx has been configured:
Write access to a protected register by a master agent function that is not the ACCEN owner.
- ReqIF-WF.Type: Requirement

###### SAJA-EHHJ-ECHB-FIHJ_reporting: Reporting
On detection of an access protection violation the GPT12 terminate the access with FPI error that is detected by the BCU, see SM[HW]:FPI:ERROR_HANDLING.
- ReqIF-WF.Type: Information

###### SAJA-EHHJ-ECHB-FIHJ_recommendederrorreaction: Recommended error reaction
System integrator to select an appropriate safe reaction in the SMU.
- ReqIF-WF.Type: Information

###### POXA-EHHJ-ECHB-DGEC: SM[HW]:GPT12:SV_AP
- IFX.Version: 1 1
- ReqIF-WF.Type: Heading

###### POXA-EHHJ-ECHB-DGEC_description: Description
Critical module registers are implemented with a write access restriction that allows access only to masters with supervisor (SV) mode privilege.
Unauthorized access attempts are blocked by this mechanism.
For a list of the registers protected by SV, see tables Register overview – access mode glossary and Register overview – GPT12 (ascending offset address) in the User Manual.
- ReqIF-WF.Type: Information

###### POXA-EHHJ-ECHB-DGEC_resetoperationalstate: Reset operational state
The safety mechanism is active after application reset.
- ReqIF-WF.Type: Information

###### POXA-EHHJ-ECHB-DGEC_configurationandactivation: Configuration and activation
N.A.
- ReqIF-WF.Type: Requirement

###### POXA-EHHJ-ECHB-DGEC_test: Test
This safety measure can be tested by an write access to a protected register by a master agent function without supervisor (SV) access rights.
- ReqIF-WF.Type: Requirement

###### POXA-EHHJ-ECHB-DGEC_reporting: Reporting
On detection of an access protection violation the GPT12 will terminate the access with FPI error that is detected by the BCU, see SM[HW]:FPI:ERROR_HANDLING.
- ReqIF-WF.Type: Information

###### POXA-EHHJ-ECHB-DGEC_recommendederrorreaction: Recommended error reaction
System integrator to select an appropriate safe reaction in the SMU.
- ReqIF-WF.Type: Information

##### TVDA-EHBA-BFHE-JBCH: Alarms
GPT12 alarms
| Alarm name | Safety mechanism | Alarm flag to be cleared in |
| --- | --- | --- |
| GPT12 PROT uncorrectable error alarm | SM[HW]:GPT12:REG_MONITOR | SMU only |
| FPI error alarm | SM[HW]:GPT12:CFG_AS_AP SM[HW]:GPT12:ENDINIT SM[HW]:GPT12:SAFETY_ENDINIT | SMU only |
- IFX.Version: 1
- ReqIF-WF.Type: Information

##### OWFA-FAFF-GAJI-EBEB: External safety mechanisms
- IFX.Version: 1
- ReqIF-WF.Type: Information

###### IKKA-EHHA-FHBB-FABB: ESM[SW]:GPT12:TIMER_REDUNDANCY
- IFX.Version: 11
- ReqIF-WF.Type: Heading

###### IKKA-EHHA-FHBB-FABB_description: Description
The application software shall configure and use two GPT12 timers redundantly to acquire digital signal from external sender. Upon capturing the signal, application software shall compare these values. In case of mismatch the application software shall trigger appropriate action. Alternatively, application could use GTM TIM or eGTM TIM redundantly with GPT12 timers.
This ESM performs the following activities
1. Initialization phase (start-up)
1. Configuration of PORTa and PORTb as alternate input
2. Configuration of GPT12x as mission
3. Configuration of GPT12y or GTM.TIM or eGTM.TIM as monitor
2. Run-time
1. Read back of configuration registers of PORTa, PORTb, GPT12x and GPT12y/GTM.TIM/eGTM.TIM once at the beginning to verify correct configuration
2. Periodically compare the results from GPT12x and GPT12y/GTM.TIM/eGTM.TIM
3. In case of mismatch
1. Application reset, if possible and repeat activity 1 and 2 to remove soft error
2. In case of repeat mismatch, transition to safe state
Note: In addition, application could use filtering function in GTM.TIM or eGTM.TIM before the digital signal could be measured by GPT12x and/or GPT12y. In this case, application shall configure GTM.TIM, eGTM.TIM, GPT12x and GPT12y during the initialization phase. Configuration shall be verified during the run-time by reading back the configuration registers.
Timer redundancy
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In order to avoid common cause failures, following implementation measure shall be considered
- Application shall use two different PORT instance for mission channel and monitor channel
- Application shall not use neighboring PORTs, pads and pins for mission and monitor channel
- If GPT12 is used as monitor channel, application shall use different GPT12 instance from mission channel
- If filtering function of GTM.TIM or eGTM.TIM is used in mission and monitor channel, application shall use different GTM or eGTM clusters for mission and monitor TIM channels
- ReqIF-WF.Type: Requirement

###### HXLA-EHHA-GDBH-EDHD: ESM[SW]:GPT12:ENCODER_PLAUSIBILITY
- IFX.Version: 1
- ReqIF-WF.Type: Heading

###### HXLA-EHHA-GDBH-EDHD_description: Description
The application shall implement system level plausibility check on the data acquired by GPT12 timers in Incremental Interface Mode.
The data for plausibility check could be acquired from one of the following
- Resolver (DS-ADC)
- Angle sensor (QSPI or SENT)
- 2nd independent GPT12 timer in Incremental Interface Mode
- Any other system level data available
This ESM performs following activities
1. Initialization phase (start-up)
1. Configuration of PORTs as alternate input
2. Configuration of GPT12x as monitor
3. Configuration of mission channel
2. Run-time
1. Read back of configuration registers of PORTs, GPT12 and mission channel to verify correct configuration
2. Periodically compare the results from mission channel and GPT12
3. In case of mismatch
1. Application reset, if possible and repeat activity 1 and 2 to remove soft error
2. In case of repeat mismatch, transition to safe state
Note: In addition, application could use filtering function in GTM.TIM or eGTM.TIM before the digital signal could be measured by GPT12. In this case, application shall configure GTM.TIM or eGTM.TIM along with GPT12 during the initialization phase. Configuration shall be verified once at the beginning by reading back the configuration registers.
Encoder plausibility
In order to avoid common cause failures, following implementation measure shall be considered
- Application shall use two different PORT instance for mission channel and monitor channel
- Application shall not use neighboring PORTs, pads and pins for mission and monitor channel
- ReqIF-WF.Type: Requirement

###### UIOA-EHHE-GBIG-DCAJ: ESM[SW]:GPT12:ISR_MONITOR
- IFX.Version: 1
- ReqIF-WF.Type: Heading

###### UIOA-EHHE-GBIG-DCAJ_description: Description
This ESM shall detect missing and unintended interrupts originating from GPT12 modules.
In this use case, two TIM channels are used redundantly to acquire the same digital signal. One TIM channel (TIMx) acts as a mission channel and the other TIM channel (TIMy or GPT12 timer) acts as a monitor. Either CPU or GTM.MCS can be used to perform plausibility checks between results of mission channel and monitor channel.
Each TIM channel is able to generate 6 individual interrupts (TIM[i]_NEWVAL[x]_IRQ, TIM[i]_ECNTOFL[x]_IRQ, TIM[i]_CNTOFL[x]_IRQ, TIM[i]_GPROFL[x]_IRQ, TIM[i]_TODET[x]_IRQ and TIM[i]_GLITCHDET[x]_IRQ ) if enabled inside the TIM channel. These six interrupts are bundled into one interrupt (TIMx_CHx_IRQ) per TIM channel connected to the ICM. GPT12 can generate three service request interrupts SR0, SR1 and SR2. If these interrupts are enabled and used in the safety related application, ESM[SW]:GPT12:ISR_MONITOR shall be implemented to detect missing and unintended interrupts. Otherwise, this safety mechanism is not required
Once the interrupt is set by EGTM.TIMy or GTM.TIMy or GPT12, application shall check for missing and unintended interrupt by comparing the SRR (service request status) bit in SRC (Service request control) register of the mission channel with the monitor channel. Interrupt service routine of mission channel interrupts shall clear the SRR bit of the monitor channel interrupt and vice versa.
On detection of a missing or unintended safety-related interrupt request, the application software shall trigger the most appropriate reaction, depending on the application.
Note: Faults in the [IR] are covered by other SMs of [IR].
- ReqIF-WF.Type: Requirement

###### VWUA-FCEC-DIHF-DBEB: ESM[SW]:GPT12:OUTPUT_MONITORING
- IFX.Version: 1
- ReqIF-WF.Type: Heading

###### VWUA-FCEC-DIHF-DBEB_description: Description
The application SW shall periodically check if the safety critical PWM signal generated by GPT12 is within the expected range by measuring the generated PWM using GPT12 and comparing against the reference value. It is assumed that MCU receives the feedback signal from external actuator
Application could configure GPT12, eGTM.TIM or GTM.TIM timer as monitor channel.
Note: eGTM and GTM might not be available in all products.
GPT12 PWM monitoring
This ESM performs the following activities during:
1. Initialization phase (start-up)
1. Configuration of GPT1 to timer reload function for PWM generation
2. Configuration of T3OUT as mission (Tx)
3. Configuration of GPT12, eGTM.TIM or GTM as monitor channel
2. Run-time
1. Read back of configuration registers of mission and monitor channel once at the beginning to verify correct configuration
2. Periodically compare the results from monitoring channel against the expected reference value
3. In case of mismatch
1. Application reset, if possible and repeat activity 1 and 2 (to remove soft error)
2. In case of repeat mismatch, transition to safe state
In order to avoid common cause failures, application shall consider the following measures:
1. Application shall use two different GPT12 instance for mission channel and monitor channel
2. Application shall not use neighboring PORTs, pads and pins for mission and monitor channel
- ReqIF-WF.Type: Requirement

#### RMXA-FBEG-FCIG-DGCD: Global System Timestamp unit (GST)
The Global System Timestamp unit (GST) has an integrated 56-bit timer that is used to timestamp captured events. A configurable increment size allows to synchronize this timer with a system time. Trigger can be scheduled to the internal timer value or after a trigger is captured.
The GST provides a timer value that is used to timestamp captured events. The timers increment can be configured so that the timers value represents a system timebase, with compensated external influences like crystal drifts and bus delays. By using this timebase, certain events on the electronic control unit (ECU) can be represented to a system time. Functionality to use a PTP signal provided by an Ethernet module as a timebase is also available.
Trigger can be generated by the GST on different configurable time values. Using an additional masking value, trigger can be also generated at different times or with a specific period. In addition, a trigger can be generated when a configurable time passed, after receiving a trigger input.
- IFX.Version: 1
- ReqIF-WF.Type: Information

##### YLOA-FBEG-FEEI-AEJJ: External safety mechanisms
- IFX.Version: 1
- ReqIF-WF.Type: Information

###### RRVA-FCDJ-CGCB-HDAA: ESM[SW]:GST:CONFIG_READBACK
- IFX.Version: 8
- ReqIF-WF.Type: Heading

###### RRVA-FCDJ-CGCB-HDAA_description: Description
To exclude hardware failures, configuration should be read back. By comparing the written and the read values, the application software can identify false values.
- ReqIF-WF.Type: Requirement

###### RRVA-FCDJ-CGCB-HDAA_resetoperationalstate: Reset operational state
The software plausibility check is not affected by any reset and fully operational.
Note: After a reset, the configuration of the GST is reset to the default value.
- ReqIF-WF.Type: Information

###### RRVA-FCDJ-CGCB-HDAA_configurationandactivation: Configuration and activation
No special configuration or activation needs to be done on hardware side.
- ReqIF-WF.Type: Requirement

###### RRVA-FCDJ-CGCB-HDAA_test: Test
The following registers should be verified by comparing the written value with the read back value after configuration:
- CFG
- CTRL
- REL
- SCREN
- ReqIF-WF.Type: Requirement

###### RRVA-FCDJ-CGCB-HDAA_reporting: Reporting
N.A.
- ReqIF-WF.Type: Information

###### RRVA-FCDJ-CGCB-HDAA_recommendederrorreaction: Recommended error reaction
If the written values are not matching the read values, the configuration should be written again.
- ReqIF-WF.Type: Information

###### GUBA-FCDJ-CGCD-DIFJ: ESM[SW]:GST:ISR_MONITOR
- IFX.Version: 1
- ReqIF-WF.Type: Heading

###### GUBA-FCDJ-CGCD-DIFJ_description: Description
This ESM shall detect missing and unintended interrupts originating from GST modules.
- ReqIF-WF.Type: Requirement

###### GUBA-FCDJ-CGCD-DIFJ_resetoperationalstate: Reset operational state
The software implemented ISR monitor is not affected by any reset and fully operational.
Note: After a reset, the configuration of the GST is reset to the default value.
- ReqIF-WF.Type: Information

###### GUBA-FCDJ-CGCD-DIFJ_configurationandactivation: Configuration and activation
The GST provides 3 interrupts:
- System counter overflow
- Cyclic buffer overflow
- Counter interrupt (counter reaches zero)
The counter interrupt can be send to PORTs and DMA as an interrupt. It is recommended to disable the DMA interrupt, when the hardware trigger should not be monitored.
- ReqIF-WF.Type: Requirement

###### GUBA-FCDJ-CGCD-DIFJ_test: Test
The system counter overflow can be verified by reading and comparing the value of the system timer. After the interrupt is triggered, it starts counting from zero again.
The cyclic buffer overflow is generated, when the last entry slot is written. This can be checked by comparing the .LWRT bitfield. It should match the maximum number of available buffer entries.
The counter interrupt can be verified by its occurrence. The cyclic buffer must have a logged trigger input that was received previous to the interrupt generation. The difference between trigger capture and interrupt request should be the number of clock cycles, stored in the register.
As the counter interrupt should occur periodically, a missing or unintended interrupt can be identified by checking in each periode the generation of the PORT and DMA interrupts.
- ReqIF-WF.Type: Requirement

###### GUBA-FCDJ-CGCD-DIFJ_reporting: Reporting
N.A.
- ReqIF-WF.Type: Information

###### GUBA-FCDJ-CGCD-DIFJ_recommendederrorreaction: Recommended error reaction
Unintended interrupts should be ignored.
- ReqIF-WF.Type: Information

###### ZROA-FDII-BCAG-AGHI: ESM[SW]:GST:LOG_PLAUSIBILITY
This ESM shall detect wrong logged sources and bad timestamps from the GST history.
In this usecase, the information provided by the GST and the interrupts captured by the Interrupt Router (IR) are taken to verify the plausibility of the logged entries in the GST internal buffer.
By comparing the logged source of an entry against the SRCENA and SCRENB registers, wrongly gated signals can be detected. In addition, by using the IR processed interrupts the correctness can be improved by detecting wrongly ungated signals as well.
To verify that the logged timestamp is plausible, the time value needs to be compared against the previous and the next logged entries timestamp value. The timestamp must lay in between both of them.
further the current value of the reference time must be greater as the timestamp of the logged entry.
- IFX.Version: 1
- ReqIF-WF.Type: Heading

##### UBDA-FDAH-BDHG-EHFH: Alarms
- IFX.Version: 1
- ReqIF-WF.Type: Information

##### LXYA-FBEG-FEEH-GGHC: Internal safety mechanisms
- IFX.Version: 1
- ReqIF-WF.Type: Information

###### AHIA-FCGJ-EHJH-JADA: SM[HW]:GST:REG_MONITOR
- IFX.Version: 5
- ReqIF-WF.Type: Heading

###### AHIA-FCGJ-EHJH-JADA_description: Description
The GST implements safety flip-flops for detecting transient or permanent faults in the configuration registers and sequential logic. Safety flip-flops are special flip-flops that implement a hardware mechanism capable to detect bit flip within the flip-flops. The configuration and control registers which are designed with safety flip-flops are listed below:
- CFG
- CTRL
- REL
- SRCEN
- TRGOUT
- CNT
- TRGEVNT
- ReqIF-WF.Type: Information

###### AHIA-FCGJ-EHJH-JADA_resetoperationalstate: Reset operational state
This safety mechanism is reset according to the reset behavior of each of the registers above, as specified in the table in the User Manual.
- ReqIF-WF.Type: Information

###### AHIA-FCGJ-EHJH-JADA_configurationandactivation: Configuration and activation
N.A.
- ReqIF-WF.Type: Requirement

###### AHIA-FCGJ-EHJH-JADA_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
During the self-test the alarms listed in Reporting section are triggered in the SMU. After the completion of the test, it is required to clear these alarms in the SMU.
- ReqIF-WF.Type: Requirement

###### AHIA-FCGJ-EHJH-JADA_reporting: Reporting
After the monitor detects a fault, an alarm will be reported on the GST SFF uncorrectable error alarm interface to SMU.
- ReqIF-WF.Type: Information

###### AHIA-FCGJ-EHJH-JADA_recommendederrorreaction: Recommended error reaction
System integrator to select appropriate safe reaction in SMU.
- ReqIF-WF.Type: Information

###### LIVA-FCDJ-CFGD-GGGE: SM[HW]:GST:ENDINIT
- IFX.Version: 4
- ReqIF-WF.Type: Heading

###### LIVA-FCDJ-CFGD-GGGE_description: Description
The GST provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – GST (ascending offset address) in the User Manual.
- ReqIF-WF.Type: Information

###### LIVA-FCDJ-CFGD-GGGE_resetoperationalstate: Reset operational state
An application reset will set the configuration of this safety mechanism back to its default value.
- ReqIF-WF.Type: Information

###### LIVA-FCDJ-CFGD-GGGE_configurationandactivation: Configuration and activation
This safety mechanism is active after intentional configuration by application software through the PROTE register.
- ReqIF-WF.Type: Requirement

###### LIVA-FCDJ-CFGD-GGGE_test: Test
This safety measure can be tested after the PROT owner has been configured:
Write access to a protected register by a master agent function that is not the PROT owner.
- ReqIF-WF.Type: Requirement

###### LIVA-FCDJ-CFGD-GGGE_reporting: Reporting
On detection of an access protection violation the GST will terminate the access with FPI error that is detected by the BCU, see SM[HW]:FPI:ERROR_HANDLING.
- ReqIF-WF.Type: Information

###### LIVA-FCDJ-CFGD-GGGE_recommendederrorreaction: Recommended error reaction
System integrator to select an appropriate safe reaction in the SMU.
- ReqIF-WF.Type: Information

###### GPKA-FCDJ-DCJH-FDIJ: SM[HW]:GST:SAFETY_ENDINIT
- IFX.Version: 1
- ReqIF-WF.Type: Heading

###### GPKA-FCDJ-DCJH-FDIJ_description: Description
The GST provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – GST (ascending offset address) in the User Manual.
- ReqIF-WF.Type: Information

###### GPKA-FCDJ-DCJH-FDIJ_resetoperationalstate: Reset operational state
The PROTSE mechanism is active after intentional configuration by application software.
- ReqIF-WF.Type: Information

###### GPKA-FCDJ-DCJH-FDIJ_configurationandactivation: Configuration and activation
This safety mechanism is active after intentional configuration by application software through the PROTSE register.
- ReqIF-WF.Type: Requirement

###### GPKA-FCDJ-DCJH-FDIJ_test: Test
This safety measure can be tested after the PROT owner has been configured:
Write access to a protected register by a master agent function that is not the PROT owner.
- ReqIF-WF.Type: Requirement

###### GPKA-FCDJ-DCJH-FDIJ_reporting: Reporting
On detection of an access protection violation the GST will terminate the access with FPI error that is detected by the BCU, see SM[HW]:FPI:ERROR_HANDLING.
- ReqIF-WF.Type: Information

###### GPKA-FCDJ-DCJH-FDIJ_recommendederrorreaction: Recommended error reaction
System integrator to select an appropriate safe reaction in the SMU.
- ReqIF-WF.Type: Information

###### OIIA-FCEH-FGHA-AEJG: SM[HW]:GST:CFG_AS_AP
- IFX.Version: 1
- ReqIF-WF.Type: Heading

###### OIIA-FCEH-FGHA-AEJG_description: Description
The GST checks if the access master agent function identifier is enabled for the type of access (read access and write access, configured through the GST ACCEN registers) to the selected register.
Unauthorized access attempts are blocked by this mechanism.
- ReqIF-WF.Type: Information

###### OIIA-FCEH-FGHA-AEJG_resetoperationalstate: Reset operational state
An application reset will set the configuration of this safety mechanism back to its default value.
- ReqIF-WF.Type: Information

###### OIIA-FCEH-FGHA-AEJG_configurationandactivation: Configuration and activation
This safety mechanism is active after intentional configuration by application software through the ACCENx registers.
- ReqIF-WF.Type: Requirement

###### OIIA-FCEH-FGHA-AEJG_test: Test
This safety measure can be tested after the ACCENx has been configured:
Write access to a protected register by a master agent function that is not the ACCEN owner.
- ReqIF-WF.Type: Requirement

###### OIIA-FCEH-FGHA-AEJG_reporting: Reporting
On detection of an access protection violation the GST terminate the access with FPI error that is detected by the BCU, see SM[HW]:FPI:ERROR_HANDLING.
- ReqIF-WF.Type: Information

###### OIIA-FCEH-FGHA-AEJG_recommendederrorreaction: Recommended error reaction
System integrator to select an appropriate safe reaction in the SMU.
- ReqIF-WF.Type: Information

###### VOKA-FCEH-FGHI-ABJC: SM[HW]:GST:SV_AP
- IFX.Version: 1
- ReqIF-WF.Type: Heading

###### VOKA-FCEH-FGHI-ABJC_description: Description
Critical module registers are implemented with a write access restriction that allows access only to masters with supervisor (SV) mode privilege.
Unauthorized access attempts are blocked by this mechanism.
For a list of the registers protected by SV, see tables Register overview – access mode glossary and Register overview – GST (ascending offset address) in the User Manual.
- ReqIF-WF.Type: Information

###### VOKA-FCEH-FGHI-ABJC_resetoperationalstate: Reset operational state
The safety mechanism is active after application reset.
- ReqIF-WF.Type: Information

###### VOKA-FCEH-FGHI-ABJC_configurationandactivation: Configuration and activation
N.A.
- ReqIF-WF.Type: Requirement

###### VOKA-FCEH-FGHI-ABJC_test: Test
This safety measure can be tested by an write access to a protected register by a master agent function without supervisor (SV) access rights.
- ReqIF-WF.Type: Requirement

###### VOKA-FCEH-FGHI-ABJC_reporting: Reporting
On detection of an access protection violation the GST will terminate the access with FPI error that is detected by the BCU, see SM[HW]:FPI:ERROR_HANDLING.
- ReqIF-WF.Type: Information

###### VOKA-FCEH-FGHI-ABJC_recommendederrorreaction: Recommended error reaction
System integrator to select an appropriate safe reaction in the SMU.
- ReqIF-WF.Type: Information

#### PBGA-EECH-GFID-ICGD: High Speed Physical Layer (HSPHY)
The High Speed PHY Block (HSPHY) is a functional block that implements physical layer blocks for Ethernet, PCIe, xSPI and SGBT I/O functions. It provides the infrastructure for high-speed communication interfaces.
The HSPHY hosts high-speed serial I/Os: The multi-protocol 8 Gbps PHY (MP8G PHY). The MP8G PHY acts as the physical layer for the supported high-speed serial interfaces and can be shared among different protocols, supported by the corresponding PCS (physical coding layer) layer.
The HSPHY includes an SPB slave interface with a set of control and status registers (CSR).
The HSPHY also hosts the IO control for MII, RMII, RGMII for GETH. Two MDIO (Management Data Input/Output) for both MAC0 and MAC1. The RGMII pad and skew control as well as the XSPI skew and pad control are implemented in this block.
- IFX.Version: 1
- ReqIF-WF.Type: Information

##### ZZPA-FAFF-GFFB-IAID: Internal safety mechanisms
- IFX.Version: 1
- ReqIF-WF.Type: Information

###### RTKA-EHEI-JGIA-EIHF: SM[HW]:HSPHY:REG_MONITOR
- IFX.Version: 1
- ReqIF-WF.Type: Heading

###### RTKA-EHEI-JGIA-EIHF_description: Description
This safety mechanism for HSPHY detects transient faults in configuration registers by using modular redundancy (safety flip-flop).
Safety flip-flops are special flip-flops that implement a hardware mechanism capable to detect bit flip within the protected registers thus preventing single point faults. The configuration and control registers which are protected with safety flip- flops are listed below:
1. CMNCFG, The common control
2. PHYy_CTRL0, control 0 for the PHYy
3. PHYy_CTRL1, control 1 for the PHYy
4. DLL_CFG, DLL configuration register
- ReqIF-WF.Type: Information

###### RTKA-EHEI-JGIA-EIHF_resetoperationalstate: Reset operational state
This safety mechanism is reset according to the reset behavior of each of the registers above, as specified in the Register Overview - HSPHY table in the User Manual.
- ReqIF-WF.Type: Information

###### RTKA-EHEI-JGIA-EIHF_configurationandactivation: Configuration and activation
N.A.
- ReqIF-WF.Type: Requirement

###### RTKA-EHEI-JGIA-EIHF_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### RTKA-EHEI-JGIA-EIHF_reporting: Reporting
Upon detection of an error, an alarm will be reported to the SMU.
- ReqIF-WF.Type: Information

###### RTKA-EHEI-JGIA-EIHF_recommendederrorreaction: Recommended error reaction
System integrator to select an appropriate safe
reaction in the SMU.
- ReqIF-WF.Type: Information

###### UERA-EHHJ-EDAC-JDAI: SM[HW]:HSPHY:ENDINIT
- IFX.Version: 10 10
- ReqIF-WF.Type: Heading

###### UERA-EHHJ-EDAC-JDAI_description: Description
The HSPHY provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – HSPHY (ascending offset address) in the User Manual.
- ReqIF-WF.Type: Information

###### UERA-EHHJ-EDAC-JDAI_resetoperationalstate: Reset operational state
An application reset will set the configuration of this safety mechanism back to its default value.
- ReqIF-WF.Type: Information

###### UERA-EHHJ-EDAC-JDAI_configurationandactivation: Configuration and activation
This safety mechanism is active after intentional configuration by application software through the PROTE register.
- ReqIF-WF.Type: Requirement

###### UERA-EHHJ-EDAC-JDAI_test: Test
This safety measure can be tested after the PROT owner has been configured:
Write access to a protected register by a master agent function that is not the PROT owner.
- ReqIF-WF.Type: Requirement

###### UERA-EHHJ-EDAC-JDAI_reporting: Reporting
On detection of an access protection violation the HSPHY terminates the access with FPI error that is detected by the BCU, see SM[HW]:FPI:ERROR_HANDLING.
- ReqIF-WF.Type: Information

###### UERA-EHHJ-EDAC-JDAI_recommendederrorreaction: Recommended error reaction
System integrator to select an appropriate safe reaction in the SMU.
- ReqIF-WF.Type: Information

###### GVBA-EHHJ-EDAC-AEFE: SM[HW]:HSPHY:SAFETY_ENDINIT
- IFX.Version: 8 8
- ReqIF-WF.Type: Heading

###### GVBA-EHHJ-EDAC-AEFE_description: Description
The HSPHY provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – HSPHY (ascending offset address) in the User Manual.
- ReqIF-WF.Type: Information

###### GVBA-EHHJ-EDAC-AEFE_resetoperationalstate: Reset operational state
An application reset will set the configuration of this safety mechanism back to its default value.
- ReqIF-WF.Type: Information

###### GVBA-EHHJ-EDAC-AEFE_configurationandactivation: Configuration and activation
This safety mechanism is active after intentional configuration by application software through the PROTSE register.
- ReqIF-WF.Type: Requirement

###### GVBA-EHHJ-EDAC-AEFE_test: Test
This safety measure can be tested after the PROT owner has been configured:
Write access to a protected register by a master agent function that is not the PROT owner.
- ReqIF-WF.Type: Requirement

###### GVBA-EHHJ-EDAC-AEFE_reporting: Reporting
On detection of an access protection violation the HSPHY terminates the access with FPI error that is detected by the BCU, see SM[HW]:FPI:ERROR_HANDLING.
- ReqIF-WF.Type: Information

###### GVBA-EHHJ-EDAC-AEFE_recommendederrorreaction: Recommended error reaction
System integrator to select an appropriate safe reaction in the SMU.
- ReqIF-WF.Type: Information

###### CCRA-EHHJ-EDAB-GFIH: SM[HW]:HSPHY:SV_AP
- IFX.Version: 7 7
- ReqIF-WF.Type: Heading

###### CCRA-EHHJ-EDAB-GFIH_description: Description
Critical module registers are implemented with a write access restriction that allows access only to masters with supervisor (SV) mode privilege.
Unauthorized access attempts are blocked by this mechanism.
For a list of the registers protected by SV, see tables Register overview – access mode glossary and Register overview – HSPHY (ascending offset address) in the User Manual.
- ReqIF-WF.Type: Information

###### CCRA-EHHJ-EDAB-GFIH_resetoperationalstate: Reset operational state
The safety mechanism is active after application reset.
- ReqIF-WF.Type: Information

###### CCRA-EHHJ-EDAB-GFIH_configurationandactivation: Configuration and activation
N.A.
- ReqIF-WF.Type: Requirement

###### CCRA-EHHJ-EDAB-GFIH_test: Test
This safety measure can be tested by an write access to a protected register by a master agent function without supervisor (SV) access rights.
- ReqIF-WF.Type: Requirement

###### CCRA-EHHJ-EDAB-GFIH_reporting: Reporting
On detection of an access protection violation the HSPHY terminates the access with FPI error that is detected by the BCU, see SM[HW]:FPI:ERROR_HANDLING.
- ReqIF-WF.Type: Information

###### CCRA-EHHJ-EDAB-GFIH_recommendederrorreaction: Recommended error reaction
System integrator to select an appropriate safe reaction in the SMU.
- ReqIF-WF.Type: Information

###### IROA-EHHJ-EDAC-JIID: SM[HW]:HSPHY:CFG_AS_AP
- IFX.Version: 1 1
- ReqIF-WF.Type: Heading

###### IROA-EHHJ-EDAC-JIID_description: Description
The HSPHY checks if the access master agent function identifier is enabled for the type of access (read access and write access, configured through the HSPHY ACCEN registers) to the selected register.
Unauthorized access attempts are blocked by this mechanism.
- ReqIF-WF.Type: Information

###### IROA-EHHJ-EDAC-JIID_resetoperationalstate: Reset operational state
An application reset will set the configuration of this safety mechanism back to its default value.
- ReqIF-WF.Type: Information

###### IROA-EHHJ-EDAC-JIID_configurationandactivation: Configuration and activation
This safety mechanism is active after intentional configuration by application software through the ACCENx registers.
- ReqIF-WF.Type: Requirement

###### IROA-EHHJ-EDAC-JIID_test: Test
This safety measure can be tested after the ACCENx has been configured:
Write access to a protected register by a master agent function that is not the ACCEN owner.
- ReqIF-WF.Type: Requirement

###### IROA-EHHJ-EDAC-JIID_reporting: Reporting
On detection of an access protection violation the HSPHY terminates the access with FPI error that is detected by the BCU, see SM[HW]:FPI:ERROR_HANDLING.
- ReqIF-WF.Type: Information

###### IROA-EHHJ-EDAC-JIID_recommendederrorreaction: Recommended error reaction
System integrator to select an appropriate safe reaction in the SMU.
- ReqIF-WF.Type: Information

##### MYJA-EHBJ-DJHE-GFII: Alarms
HSPHY alarms
| Alarm name | Safety mechanism | Alarm flag to be cleared in |
| --- | --- | --- |
| HSPHY SFF uncorrectable error alarm | SM[HW]:HSPHY:REG_MONITOR | SMU only |
| FPI error alarm | SM[HW]:HSPHY:SV_AP SM[HW]:HSPHY:CFG_AS_AP SM[HW]:HSPHY:ENDINIT SM[HW]:HSPHY:SAFETY_ENDINIT | SMU only |
- IFX.Version: 1
- ReqIF-WF.Type: Information

##### TYQA-FAFF-GFFC-EAAD: External safety mechanisms
- IFX.Version: 1
- ReqIF-WF.Type: Information

#### JOSA-EDCJ-DCBG-CEFD: Inter-Integrated Circuit (I2C)
The I2C module is a functional block that offers communication functionality according to the I2C-bus specification version 2.1. I2C includes an SPB slave interface with a set of special function registers (SFRs).
- IFX.Version: 1
- ReqIF-WF.Type: Information

##### KYPA-FAFF-HJGF-FIDA: Internal safety mechanisms
- IFX.Version: 1
- ReqIF-WF.Type: Information

###### LWZA-EHHJ-EDHA-DAJD: SM[HW]:I2C:ENDINIT
- IFX.Version: 6 6
- ReqIF-WF.Type: Heading

###### LWZA-EHHJ-EDHA-DAJD_description: Description
The I2C provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – I2C (ascending offset address) in the User Manual.
- ReqIF-WF.Type: Information

###### LWZA-EHHJ-EDHA-DAJD_resetoperationalstate: Reset operational state
An application reset will set the configuration of this safety mechanism back to its default value.
- ReqIF-WF.Type: Information

###### LWZA-EHHJ-EDHA-DAJD_configurationandactivation: Configuration and activation
This safety mechanism is active after intentional configuration by application software through the PROTE register.
- ReqIF-WF.Type: Requirement

###### LWZA-EHHJ-EDHA-DAJD_test: Test
This safety measure can be tested after the PROT owner has been configured:
Write access to a protected register by a master agent function that is not the PROT owner.
- ReqIF-WF.Type: Requirement

###### LWZA-EHHJ-EDHA-DAJD_reporting: Reporting
On detection of an access protection violation the I2C will terminate the access with FPI error that is detected by the BCU, see SM[HW]:FPI:ERROR_HANDLING.
- ReqIF-WF.Type: Information

###### LWZA-EHHJ-EDHA-DAJD_recommendederrorreaction: Recommended error reaction
System integrator to select an appropriate safe reaction in the SMU.
- ReqIF-WF.Type: Information

###### QBWA-EHHJ-EDHA-EBEE: SM[HW]:I2C:SAFETY_ENDINIT
- IFX.Version: 1 1
- ReqIF-WF.Type: Heading

###### QBWA-EHHJ-EDHA-EBEE_description: Description
The I2C provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – I2C (ascending offset address) in the User Manual.
- ReqIF-WF.Type: Information

###### QBWA-EHHJ-EDHA-EBEE_resetoperationalstate: Reset operational state
An application reset will set the configuration of this safety mechanism back to its default value.
- ReqIF-WF.Type: Information

###### QBWA-EHHJ-EDHA-EBEE_configurationandactivation: Configuration and activation
This safety mechanism is active after intentional configuration by application software through the PROTSE register.
- ReqIF-WF.Type: Requirement

###### QBWA-EHHJ-EDHA-EBEE_test: Test
This safety measure can be tested after the PROT owner has been configured:
Write access to a protected register by a master agent function that is not the PROT owner.
- ReqIF-WF.Type: Requirement

###### QBWA-EHHJ-EDHA-EBEE_reporting: Reporting
On detection of an access protection violation the I2C will terminate the access with FPI error that is detected by the BCU, see SM[HW]:FPI:ERROR_HANDLING.
- ReqIF-WF.Type: Information

###### QBWA-EHHJ-EDHA-EBEE_recommendederrorreaction: Recommended error reaction
System integrator to select an appropriate safe reaction in the SMU.
- ReqIF-WF.Type: Information

###### RJRA-EHHJ-EDHA-DFIF: SM[HW]:I2C:CFG_AS_AP
- IFX.Version: 4 4
- ReqIF-WF.Type: Heading

###### RJRA-EHHJ-EDHA-DFIF_description: Description
The I2C checks if the access master agent function identifier is enabled for the type of access (read access and write access, configured through the I2C ACCEN registers) to the selected register.
Unauthorized access attempts are blocked by this mechanism.
- ReqIF-WF.Type: Information

###### RJRA-EHHJ-EDHA-DFIF_resetoperationalstate: Reset operational state
An application reset will set the configuration of this safety mechanism back to its default value.
- ReqIF-WF.Type: Information

###### RJRA-EHHJ-EDHA-DFIF_configurationandactivation: Configuration and activation
This safety mechanism is active after intentional configuration by application software through the ACCENx registers.
- ReqIF-WF.Type: Requirement

###### RJRA-EHHJ-EDHA-DFIF_test: Test
This safety measure can be tested after the ACCENx has been configured:
Write access to a protected register by a master agent function that is not the ACCEN owner.
- ReqIF-WF.Type: Requirement

###### RJRA-EHHJ-EDHA-DFIF_reporting: Reporting
On detection of an access protection violation the I2C terminate the access with FPI error that is detected by the BCU, see SM[HW]:FPI:ERROR_HANDLING.
- ReqIF-WF.Type: Information

###### RJRA-EHHJ-EDHA-DFIF_recommendederrorreaction: Recommended error reaction
System integrator to select an appropriate safe reaction in the SMU.
- ReqIF-WF.Type: Information

###### ARKA-EHHJ-EDHA-AHIC: SM[HW]:I2C:SV_AP
- IFX.Version: 4 4
- ReqIF-WF.Type: Heading

###### ARKA-EHHJ-EDHA-AHIC_description: Description
Critical module registers are implemented with a write access restriction that allows access only to masters with supervisor (SV) mode privilege.
Unauthorized access attempts are blocked by this mechanism.
For a list of the registers protected by SV, see tables Register overview – access mode glossary and Register overview – I2C (ascending offset address) in the User Manual.
- ReqIF-WF.Type: Information

###### ARKA-EHHJ-EDHA-AHIC_resetoperationalstate: Reset operational state
The safety mechanism is active after application reset.
- ReqIF-WF.Type: Information

###### ARKA-EHHJ-EDHA-AHIC_configurationandactivation: Configuration and activation
N.A.
- ReqIF-WF.Type: Requirement

###### ARKA-EHHJ-EDHA-AHIC_test: Test
This safety measure can be tested by an write access to a protected register by a master agent function without supervisor (SV) access rights.
- ReqIF-WF.Type: Requirement

###### ARKA-EHHJ-EDHA-AHIC_reporting: Reporting
On detection of an access protection violation the I2C will terminate the access with FPI error that is detected by the BCU, see SM[HW]:FPI:ERROR_HANDLING.
- ReqIF-WF.Type: Information

###### ARKA-EHHJ-EDHA-AHIC_recommendederrorreaction: Recommended error reaction
System integrator to select an appropriate safe reaction in the SMU.
- ReqIF-WF.Type: Information

##### ONCA-EHBJ-DGGH-EDDD: Alarms
I2C alarms
| Alarm name | Safety mechanism | Alarm flag to be cleared in |
| --- | --- | --- |
| FPI error alarm | SM[HW]:I2C:SV_AP SM[HW]:I2C:CFG_AS_AP SM[HW]:I2C:ENDINIT SM[HW]:I2C:SAFETY_ENDINIT | SMU only |
- IFX.Version: 1
- ReqIF-WF.Type: Information

##### LSCA-FAFF-HJGD-BEDI: External safety mechanisms
- IFX.Version: 1
- ReqIF-WF.Type: Information

###### CWUA-EHEH-BIDG-AJDC: ESM[SW]:I2C:SAFE_COMMUNICATION
Description
Random hardware faults in the communication controller or in the communication interface can lead to corruption or loss of safety related data carried by a communication frame. In-order to detect the causes or effects of such communication faults, the application software has to implement safe End-to-End communication protecting the safety critical data.
The Safe End-to-End communication has to be implemented by application software of both the sender and the receiver of a communication frame. The sender appends an "E2E header" containing safety elements such as CRC or Counter to the communication data. The receivers evaluates the safety elements contained in the E2E header of the communication frame in order to detect faults. Figure below shows an example layout and construction of a communication frame protected by Safe End-to-End communication.
Safe End-to-End communication
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The following section describes the safety elements contained in the E2E header
Cyclic Redundancy Check (CRC): The CRC is calculated by the sender for the contents of the safety critical communication data. The CRC protects against data corruption. The user is responsible for choosing an appropriate CRC polynomial with sufficient Hamming Distance to provide required error detection capability for a corresponding length of communication data. It is recommended to use a different CRC polynomial that the one used by the communication controller (if any) to provide redundancy. The receiver evaluates the CRC in the E2E header of the received communication frame to detect data corruption. A mismatch of the computed CRC value compared to the received CRC value indicates occurrence of data corruption.
Counter: The Counter enables to detect faults such as loss of data, repetition of data. The sender for a given application data, inserts a counter value to the E2E header. The counter value is incremented for every transmission of the application data. The receiver evaluates the counter value in the E2E header of the received communication frame with an expected counter value. The following error scenarios can be detected
- Repetition of frame - The received counter values is same as that of the previous counter value
- Loss of frame(s) - The received counter value is non–consecutive
The receiver upon successful evaluation of the received communication frame increments the corresponding current counter value.
The application software can combine the counter value with a timer to detect delayed communication or block in the communication interface. Example: a timer (for example the system timer (STM)) can be configured to trigger a periodic check of the counter value of the associated application data. If the counter value does not change for a given time interval (for example within an FTTI), then delayed communication or block in communication is detected.
- IFX.Version: 1
- ReqIF-WF.Type: Heading

###### AHJA-EHEH-BIHF-HBHG: ESM[SW]:I2C:CHANNEL_REDUNDANCY
Faults in the following functions of I2C can be detected by implementing I2C communication over 2 independent channels
- Transmit : The I2C receives data from application software and sends it to an external I2C device or sensor
- Receive :The I2C receives data from an external I2C device or sensor and routes it to application software for further processing
The figure below shows an illustration for implementing a redundant I2C communication channel. One of the redundant I2C communication channel can be assigned as "Mission" channel (highlighted in blue) and the other can be used as a "Monitoring" channel (highlighted in green).
I2C channel redundancy
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In order to prevent common cause faults, the redundant I2C communication channels have to be independent of each other. This can be achieved by:
- Using separate I2C modules as mission and monitoring communication channel
- Both channels need to have similar configurations
- Other supporting blocks (for example PORTS) need have similarl configurations to enable the communication, for example driver strength and pull-up
- Using independent package pins and PORTS instances
Please refer to the chapter “Safety related information for package” of the safety manual to find out which pins and modules are independent of each other.
Reception of data
As soon as one of the channels receives a frame a synchronization mechanism needs to be triggered. If this synchronization identifies two matching packets, then the lockstep CPU needs to compare the packet content. If the content of Mission- and Monitoring channel match within an FTTI, then the data is considered as safe. The data comparison may optionally contain application level plausibility checks on result value bounds.
Possible synchronization techniques are:
1. Flag based synchronization
On receiving a frame a corresponding flag is set (Mission flag or Monitoring flag)
- If both flags are set within FTTI, then synchronization is OK. This situation will trigger frame comparison and flag reset
- If only one flag is set at the end of FTTI and the corresponding channel receives another packet, this is an error
2. Packet number
On receiving a frame a corresponding counter is increased (Mission counter or Monitoring counter)
- If the counters match within FTTI, then synchronization is ok and a comparison can be triggered
- If the counters have a difference greater than one at the end of FTTI, then an error has occurred
3. Timestamp from system timer
Each channel features a timestamp variable (Mission timestamp or Monitoring timestamp) stored on safe memory (for example DSPR).
- Both timestamp variables are initialized with a value equal to zero
- On receiving a frame the corresponding timestamp variables (Mission timestamp and Monitoring timestamp) are updated from a safe timer (for example System Timer (STM))
- As soon as both timestamp variables are different to zero a comparison by lockstep CPU of frame data and time window is triggered. This also sets both timestamp variables to zero
- If a channel receives a frame and its corresponding timestamp variable is not zero, then an error is detected
- If the timestamp variable values differ by more than a predefined time window, then an error is detected
- The system integrator shall ensure that the timestamp variables are checked at least once per FTTI, either with a periodic trigger or by ensuring that the message rate is at least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
Upon detection of an error the application software shall trigger an appropriate reaction.
Transmission of data
The application SW prepares frames containing the same data on Mission and Monitoring channel. Then both channels are triggered.
Interrupts
If the application software uses interrupts of I2C to service the mission and monitoring channel then to detect missing or unintended interrupts, the application software shall check if the interrupts arriving from mission channel are also arriving from the monitoring channel within an FTTI. If the presence of only one of the interrupts is detected at end of the FTTI, the application software shall trigger an error signal and an appropriate reaction.
- IFX.Version: 10
- ReqIF-WF.Type: Heading

###### AHJA-EHEH-BIHF-HBHG_description: Description
- ReqIF-WF.Type: Requirement

###### AINA-EHHE-GBDC-BDIH: ESM[SW]:I2C:ISR_MONITOR
This ESM shall detect missing or unintended interrupts originating from the I2C module. Usage of interrupts in this FB depends on the use cases and code implementation
- IFX.Version: 1
- ReqIF-WF.Type: Heading

###### AINA-EHHE-GBDC-BDIH_description: Description
Use Case: Single communication channel:
Safe single channel communication requires the application of end-to-end communication protection (see ESM[SW]:I2C:SAFE_COMMUNICATION).
Transmit/Receive interrupts
The I2C module signals to the application software that a message was received by triggering the interrupts I2C_IR_DTR, I2C_IR_P. Similarly, a transmitted message is signaled by triggering the interrupts I2C_IR_DTR, I2C_IR_P. To detect individual missing or unintended send or receive interrupts, the system integrator shall use the properties of ESM[SW]:I2C:SAFE_COMMUNICATION (e.g. timestamp or frame counter). For example, a repeated receive frame counter value indicates that an unintended receive interrupt has occurred. Interrupts missing altogether are covered by the timeout mechanism of ESM[SW]:I2C:SAFE_COMMUNICATION.
Other interrupts:
I2C notifies error events through I2C_IR_ERR interrupt. An unintended or missing interrupt of I2C_IR_ERR are also covered by ESM[SW]:I2C:SAFE_COMMUNICATION
Unused interrupt signals:
The application software shall disable any interrupts not being used in the I2C_ERRIRQSM, I2C_PIRQSM, I2C_IMSC registers and in the corresponding Interrupt Router SRC register.
- ReqIF-WF.Type: Requirement

###### AINA-EHHE-GBDC-BDIH_reactiontomissingorunintendedinterrupts: Reaction to missing or unintended interrupts
On detection of a missing or unintended safety-related interrupt request, the [Application SW] shall trigger the most appropriate reaction, depending on the application.
- ReqIF-WF.Type: Information

#### CAJA-EDCJ-DDDC-EHDB: Interrupt Router (IR)
The interrupt router receives interrupts from external resources, internal functional blocks and from application software and forwards them as service requests to the interrupt targets (CPUs, DMAs, GTM, and the PPU). These interrupt targets are referred to as interrupt service providers (ISP).
The IR converts the interrupt events from functional blocks and application software into service requests (SR) by adding configurable information, such as which interrupt target, service request priority number, and service request security information.
Note: Unless otherwise stated,´CPUs´ means ´all TriCore™ CPUs´, which includes CPUx and the CPUCS.
- IFX.Version: 1
- ReqIF-WF.Type: Information

##### POHA-EFDC-GFGI-GGFI: Internal safety mechanisms
- IFX.Version: 1
- ReqIF-WF.Type: Information

###### WLHA-EHGJ-DADH-EGCE: SM[HW]:IR:LOCKSTEP
- IFX.Version: 1
- ReqIF-WF.Type: Heading

###### WLHA-EHGJ-DADH-EGCE_description: Description
The lockstep detects permanent and transient faults in the operation of a hardware element. Two symmetrical hardware modules perform duplicate operations in lockstep (or delayed by a fixed period) and the results are compared. Any mismatch results in an error condition.
A hardware based self-test detects latent faults in the lockstep and a software based test detects latent faults in the alarm.
The hardware element implements hardware redundancy by instancing two hardware modules known as the master and the checker, as well as a comparator. The two hardware modules use the same input data and perform the same function. During each clock cycle the comparator compares the master output against the checker output. If the comparator matches the master and checker output, the hardware element has performed the expected function. If there is a mismatch, the comparator has detected a fault in the operation of the hardware element and the comparator generates an alarm.
The lockstep is a variant of hardware redundancy that introduces a temporal separation between the master and checker:
- Every input to the checker is delayed by two clock cycles
- Every output from the master is delayed by two clock cycles
The comparator performs the output check two clock cycles after the master delivered the function output. The lockstep has no effect on the nominal operation.
Lockstep
- ReqIF-WF.Type: Information

###### WLHA-EHGJ-DADH-EGCE_resetoperationalstate: Reset operational state
This safety mechanism is enabled after application reset.
- ReqIF-WF.Type: Information

###### WLHA-EHGJ-DADH-EGCE_configurationandactivation: Configuration and activation
N.A.
- ReqIF-WF.Type: Requirement

###### WLHA-EHGJ-DADH-EGCE_test: Test
See SM[HW]:IR:LOCKSTEP_SCC.
- ReqIF-WF.Type: Requirement

###### WLHA-EHGJ-DADH-EGCE_reporting: Reporting
If this safety mechanism detects a fault, the IR generates a IR lockstep mismatch alarm.
- ReqIF-WF.Type: Information

###### WLHA-EHGJ-DADH-EGCE_recommendederrorreaction: Recommended error reaction
System integrator to select appropriate safe reaction in SMU.
- ReqIF-WF.Type: Information

###### AOHA-EHGJ-DAEJ-IBCJ: SM[HW]:IR:LOCKSTEP_SCC
- IFX.Version: 6
- ReqIF-WF.Type: Heading

###### AOHA-EHGJ-DAEJ-IBCJ_description: Description
The lockstep incorporates a hardware-based self-test. The self-test function sequentially injects faults into each comparator node. The lockstep detects that the fault was routed to the correct comparator node. If the fault was not routed to the correct comparator node or a real fault was detected, the lockstep generates an alarm.
The equivalent circuit for a lockstep comparator node with fault injection inputs is shown below. The self-test function injects faults into both the master and checker inputs of the critical outputs and qualified outputs.
Lockstep comparator node
The self-test function uses a free-running, binary counter using gray code number representation known as the input counter to calculate which comparator node will be tested in a given clock cycle. The self-test function will test every comparator node once every 8192 clock cycles. Alternate cycles of the self-test function will inject faults into either the master or checker side of a lockstep comparator node. A complete cycle of the self-test function will repeat every 16384 clock cycles. Injecting a fault into either side of a lockstep comparator node will cause the lockstep comparator node to fail unless a real fault occurs in the same clock cycle in which case the two faults will cancel out.
A second binary counter known as the monitor counter checks that the input counter has injected the fault into the intended lockstep comparator node. If the input counter and the monitor counter match the same comparator node and detect an injected fault, the lockstep will not generate an alarm. In the event a real fault has occurred the lockstep will generate an IR lockstep mismatch alarm.
The following faults will be detected:
- An actual fault occurring at any of the master or checker inputs
- Includes the case of the actual fault coinciding with an injected fault
- A stuck at fault occurring at any of the comparator outputs
- A stuck at fault on signal x
- A stuck at fault on signal y
- A transient error occurring in the input counter
- A transient error occurring in the monitor counter
- ReqIF-WF.Type: Information

###### AOHA-EHGJ-DAEJ-IBCJ_resetoperationalstate: Reset operational state
This safety mechanism is enabled after application reset.
- ReqIF-WF.Type: Information

###### AOHA-EHGJ-DAEJ-IBCJ_configurationandactivation: Configuration and activation
N.A.
- ReqIF-WF.Type: Requirement

###### AOHA-EHGJ-DAEJ-IBCJ_test: Test
The self-test function (triggered by setting LCLTEST.LCLT = 1) provides the application software with the ability to generate a lockstep alarm by injecting an error condition into the lockstep comparator.
The following faults will be detected:
- A stuck at fault on the alarm signal path
- ReqIF-WF.Type: Requirement

###### AOHA-EHGJ-DAEJ-IBCJ_reporting: Reporting
If this safety mechanism detects a fault, the IR generates an IR lockstep mismatch alarm.
- ReqIF-WF.Type: Information

###### AOHA-EHGJ-DAEJ-IBCJ_recommendederrorreaction: Recommended error reaction
System integrator to select appropriate safe reaction in SMU.
- ReqIF-WF.Type: Information

###### RTXA-EHGA-BAJF-CIIG: SM[HW]:IR:ICU_MONITOR
- IFX.Version: 1
- ReqIF-WF.Type: Heading

###### RTXA-EHGA-BAJF-CIIG_description: Description
The interface between interrupt control unit (ICU) and the interrupt service provider (ISP) is EDC protected by the ICU.
The ICU uses an ECC encoding of the service request (SR) information which is only used for error detection.
This means:
- The ICU generates an ECC value for the SR information signaled to the ISP and signals it together with the SR information to the ISP
- When the ISP has accepted a service request, it signals the service request information together with the ECC value back to the ICU
- After the ICU has received the information of an accepted service request from the ISP, it generates a new ECC value and compares this ECC value with the received ECC value from the ISP
- On detection of an ECC mismatch (received ECC in contrast to ECC value generated for the received information), an alarm is signaled to the SMU and the received SR information together with the received ECC value is captured in the ICU ECR register
- On detection of an ECC mismatch
- the related service request node (SRN) is not cleared
- the related LWSRx.STATUS bit is not cleared
- an Alarm_NCS to SMU_SAFE if the received SR information shows CS = 0.
- an Alarm_CS to the SMU_CS if the received SR information shows CS = 1
- information of SR is shown in LASR and ECR. For SR with CS = 1 only if enabled through CSRM CSAV control information
The ECC protection covers the following SR information:
- SRPN[7:0] (Service Request Priority Number)
- VM[2:0] (SR Virtual Machine information)
- IDX[10:0] (SR Index number of the related Service Request Node)
- CS (SR Security Information)
Note: ICU signals information to the ISP with either VALID=1 or INVALID=1. The information signaled through INVALID=1 will not be acknowledged by the CPU and therefore not ECC checked in the ICU.
For more information see IR User´s Manual chapter ´EDC protection of the ICU interface´.
ICU Interface with EDC protection
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- ReqIF-WF.Type: Information

###### RTXA-EHGA-BAJF-CIIG_resetoperationalstate: Reset operational state
The safety mechanism is active after application reset.
- ReqIF-WF.Type: Information

###### RTXA-EHGA-BAJF-CIIG_configurationandactivation: Configuration and activation
N.A.
- ReqIF-WF.Type: Requirement

###### RTXA-EHGA-BAJF-CIIG_test: Test
The ICU error detection mechanism and the related alarm signals can be tested for each ICUx separately through the EGENx register.
For more information see IR User´s Manual chapter ´EDC protection of the ICU interface´ in the sub-chapter ´EDC error injection, alarm test´
- ReqIF-WF.Type: Requirement

###### RTXA-EHGA-BAJF-CIIG_reporting: Reporting
On detection of an EDC error an alarm is signaled to the SMU.
- ReqIF-WF.Type: Information

###### RTXA-EHGA-BAJF-CIIG_recommendederrorreaction: Recommended error reaction
System integrator to select appropriate safe reaction in SMU.
- ReqIF-WF.Type: Information

###### GBWA-EHGA-CJEA-CAAJ: SM[HW]:IR:CFG_AS_AP
- IFX.Version: 1 1
- ReqIF-WF.Type: Heading

###### GBWA-EHGA-CJEA-CAAJ_description: Description
The IR checks if the access master agent function identifier is enabled for the type of access (read access and write access, configured through the IR ACCEN registers) to the selected register.
Unauthorized access attempts are blocked by this mechanism.
- ReqIF-WF.Type: Information

###### GBWA-EHGA-CJEA-CAAJ_resetoperationalstate: Reset operational state
An application reset will set the configuration of this safety mechanism back to its default value.
- ReqIF-WF.Type: Information

###### GBWA-EHGA-CJEA-CAAJ_configurationandactivation: Configuration and activation
This safety mechanism is active after intentional configuration by application software through the ACCENx registers.
- ReqIF-WF.Type: Requirement

###### GBWA-EHGA-CJEA-CAAJ_test: Test
This safety measure can be tested after the ACCENx has been configured:
- Write access to a protected register by a master agent function that is not the ACCEN owner
- ReqIF-WF.Type: Requirement

###### GBWA-EHGA-CJEA-CAAJ_reporting: Reporting
On detection of an access protection violation the IR terminate the access with FPI error that is detected by the BCU, see SM[HW]:FPI:ERROR_HANDLING.
- ReqIF-WF.Type: Information

###### GBWA-EHGA-CJEA-CAAJ_recommendederrorreaction: Recommended error reaction
System integrator to select an appropriate safe reaction in the SMU.
- ReqIF-WF.Type: Information

###### DKOA-EHGA-CJDD-GDGB: SM[HW]:IR:SAFETY_ENDINIT
- IFX.Version: 1 1
- ReqIF-WF.Type: Heading

###### DKOA-EHGA-CJDD-GDGB_description: Description
The IR provides PROT mechanisms (PROTSE, PROTCSE, PROTTOSx) that protect the configuration of the access protection mechanism (ACCEN).
The ACCEN mechanism is based on the Master Agent Function identifier. Other individual registers are also protected by these PROT mechanisms.
This supports IR freedom from interference of different SW tasks. Unauthorized access attempts are blocked by this mechanism.
For a list of the registers protected by PROTSE, PROTCSE and PROTTOSx, see the chapter “Registers of INT” in the User Manual.
- ReqIF-WF.Type: Information

###### DKOA-EHGA-CJDD-GDGB_resetoperationalstate: Reset operational state
An application reset will set the configuration of this safety mechanism back to its default value.
- ReqIF-WF.Type: Information

###### DKOA-EHGA-CJDD-GDGB_configurationandactivation: Configuration and activation
This safety mechanism is active after intentional configuration by application software through the PROTSE, PROTCSE, PROTTOSx registers.
- ReqIF-WF.Type: Requirement

###### DKOA-EHGA-CJDD-GDGB_test: Test
This safety measure can be tested after the PROT owner has been configured:
- Write access to a protected register by a master agent function that is not the PROT owner
- ReqIF-WF.Type: Requirement

###### DKOA-EHGA-CJDD-GDGB_reporting: Reporting
On detection of an access protection violation the IR will terminate the access with FPI error that is detected by the BCU, see SM[HW]:FPI:ERROR_HANDLING.
- ReqIF-WF.Type: Information

###### DKOA-EHGA-CJDD-GDGB_recommendederrorreaction: Recommended error reaction
System integrator to select an appropriate safe reaction in the SMU.
- ReqIF-WF.Type: Information

###### YWFA-EHGD-FDGG-HGCH: SM[HW]:IR:SV_AP
- IFX.Version: 9 9
- ReqIF-WF.Type: Heading

###### YWFA-EHGD-FDGG-HGCH_description: Description
Critical module registers are implemented with a write access restriction that allows access only to masters with supervisor (SV) mode privilege.
Unauthorized access attempts are blocked by this mechanism.
For a list of the registers protected by SV, see tables Register overview – access mode glossary and Register overview – IR (ascending offset address) in the User Manual.
- ReqIF-WF.Type: Information

###### YWFA-EHGD-FDGG-HGCH_resetoperationalstate: Reset operational state
The safety mechanism is active after application reset.
- ReqIF-WF.Type: Information

###### YWFA-EHGD-FDGG-HGCH_configurationandactivation: Configuration and activation
N.A.
- ReqIF-WF.Type: Requirement

###### YWFA-EHGD-FDGG-HGCH_test: Test
This safety measure can be tested by an write access to a protected register by a master agent function without supervisor (SV) access rights.
- ReqIF-WF.Type: Requirement

###### YWFA-EHGD-FDGG-HGCH_reporting: Reporting
On detection of an access protection violation the IR will terminate the access with FPI error that is detected by the BCU, see SM[HW]:FPI:ERROR_HANDLING.
- ReqIF-WF.Type: Information

###### YWFA-EHGD-FDGG-HGCH_recommendederrorreaction: Recommended error reaction
System integrator to select an appropriate safe reaction in the SMU.
- ReqIF-WF.Type: Information

##### CCRA-EHBA-BDEI-EGBB: Alarms
IR alarms
| Alarm name | Safety mechanism | Alarm flag to be cleared in |
| --- | --- | --- |
| IR lockstep mismatch alarm | SM[HW]:IR:LOCKSTEP SM[HW]:IR:LOCKSTEP_SCC | SMU only |
| IR EDC error alarm (Alarm_NCS) | SM[HW]:IR:ISP_MONITOR | SMU only |
| IR EDC error alarm (Alarm_CS) | SM[HW]:IR:ISP_MONITOR | SMU only |
| FPI error alarm (Alarm_NCS) | SM[HW]:IR:SV_AP SM[HW]:IR:CFG_AS_AP SM[HW]:IR:SAFETY_ENDINIT | SMU only |
| FPI error alarm (Alarm_CS) | SM[HW]:IR:SV_AP SM[HW]:IR:CFG_AS_AP SM[HW]:IR:SAFETY_ENDINIT | SMU only |
- IFX.Version: 1
- ReqIF-WF.Type: Information

##### KDQA-FAED-HJGG-IDHA: External safety mechanisms
- IFX.Version: 1
- ReqIF-WF.Type: Information

###### AGJA-EHGD-EHGI-BICB: ESM[SW]:IR:CONFIG_READBACK
- IFX.Version: 10
- ReqIF-WF.Type: Heading

###### AGJA-EHGD-EHGI-BICB_description: Description
Software can detect missing writes to configuration registers by reading them back after configuration. Single occurrence of missing write transactions can be handled by repeating the missing write. Frequent errors of this type can have various reasons i.e. from disturbed operating conditional to permanent hardware faults. Generally a device reset is advisable.
The following registers of the IR configuration have to be read back after configuration:
- PROT registers
- ACCEN registers
- SRC registers after a write that changes a SRC configuration information
- VMEN registers
- ECTRL registers
- ReqIF-WF.Type: Requirement

###### SEXA-FBCF-EHDF-EEFJ: ESM[SW]:IR:FFI_AVOIDANCE
- IFX.Version: 7
- ReqIF-WF.Type: Heading

###### SEXA-FBCF-EHDF-EEFJ_description: Description
The application software shall disable unused interrupts originating from functional blocks used in the context of a non-safety related application.
These shall be deactivated in two places:
- in the related service request control (SRC) registers in IR
- in the functional block that is the source of the interrupt
Note: as an example, a CAN node could be used to communicate in the context of a non-safety related application. The unused interrupts of that node shall be disabled as stated above.
- ReqIF-WF.Type: Requirement

#### FOIA-FACA-BFBG-EDEB: Lite Ethernet (LETH)
The Lite Ethernet (LETH) is a functional block that implements Ethernet functions. LETH is connected to SRI with a master interface and with a slave interface with a set of special function registers (SFRs).
- ReqIF-WF.Type: Information

##### POAA-FAFF-HADE-IEBG: Internal safety mechanisms
- IFX.Version: 1
- ReqIF-WF.Type: Information

###### UMLA-FBBD-GDHI-AIGJ: SM[HW]:LETH:CFG_AS_AP
- IFX.Version: 6
- ReqIF-WF.Type: Heading

###### UMLA-FBBD-GDHI-AIGJ_description: Description
The LETH checks if the access master agent function identifier is enabled for the type of access (read access and write access, configured through the LETH ACCEN registers) to the selected register.
Unauthorized access attempts are blocked by this mechanism.
- ReqIF-WF.Type: Information

###### UMLA-FBBD-GDHI-AIGJ_resetoperationalstate: Reset operational state
An application reset will set the configuration of this safety mechanism back to its default value.
- ReqIF-WF.Type: Information

###### UMLA-FBBD-GDHI-AIGJ_configurationandactivation: Configuration and activation
This safety mechanism is active after intentional configuration by application software through the ACCENx registers.
- ReqIF-WF.Type: Requirement

###### UMLA-FBBD-GDHI-AIGJ_test: Test
This safety measure can be tested after the ACCENx has been configured:
Write access to a protected register by a master agent function that is not the ACCEN owner.
- ReqIF-WF.Type: Requirement

###### UMLA-FBBD-GDHI-AIGJ_reporting: Reporting
On detection of an write access protection violation the LETH will terminate the access and generate an LETH_DATAADDR alarm. On detection of a read access protection violation the LETH will terminate the access with SRI error that is detected by the XBAR, see SM[HW]:SRI:ERROR_HANDLING.
- ReqIF-WF.Type: Information

###### UMLA-FBBD-GDHI-AIGJ_recommendederrorreaction: Recommended error reaction
System integrator to select an appropriate safe reaction in the SMU.
- ReqIF-WF.Type: Information

###### ZMCA-FBBD-GDIE-HBJD: SM[HW]:LETH:SV_AP
- IFX.Version: 1
- ReqIF-WF.Type: Heading

###### ZMCA-FBBD-GDIE-HBJD_description: Description
Critical module registers are implemented with a write access restriction that allows access only to masters with supervisor (SV) mode privilege.
Unauthorized access attempts are blocked by this mechanism.
For a list of the registers protected by SV, see tables Register overview – access mode glossary and Register overview – LETH (ascending offset address) in the User Manual.
- ReqIF-WF.Type: Information

###### ZMCA-FBBD-GDIE-HBJD_resetoperationalstate: Reset operational state
The safety mechanism is active after application reset.
- ReqIF-WF.Type: Information

###### ZMCA-FBBD-GDIE-HBJD_configurationandactivation: Configuration and activation
N.A.
- ReqIF-WF.Type: Requirement

###### ZMCA-FBBD-GDIE-HBJD_test: Test
This safety measure can be tested by an write access to a protected register by a master agent function without supervisor (SV) access rights.
- ReqIF-WF.Type: Requirement

###### ZMCA-FBBD-GDIE-HBJD_reporting: Reporting
On detection of an access protection violation the LETH will terminate the access with SRI error that is detected by the XBAR, see SM[HW]:SRI:ERROR_HANDLING.
- ReqIF-WF.Type: Information

###### ZMCA-FBBD-GDIE-HBJD_recommendederrorreaction: Recommended error reaction
System integrator to select an appropriate safe reaction in the SMU.
- ReqIF-WF.Type: Information

###### HTPA-FBBD-GEJA-CGIA: SM[HW]:LETH:SAFETY_ENDINIT
- IFX.Version: 1
- ReqIF-WF.Type: Heading

###### HTPA-FBBD-GEJA-CGIA_description: Description
The LETH provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – LETH (ascending offset address) in the User Manual.
- ReqIF-WF.Type: Information

###### HTPA-FBBD-GEJA-CGIA_resetoperationalstate: Reset operational state
An application reset will set the configuration of this safety mechanism back to its default value.
- ReqIF-WF.Type: Information

###### HTPA-FBBD-GEJA-CGIA_configurationandactivation: Configuration and activation
This safety mechanism is active after intentional configuration by application software through the PROTSE register.
- ReqIF-WF.Type: Requirement

###### HTPA-FBBD-GEJA-CGIA_test: Test
This safety measure can be tested after the PROT owner has been configured:
Write access to a protected register by a master agent function that is not the PROT owner.
- ReqIF-WF.Type: Requirement

###### HTPA-FBBD-GEJA-CGIA_reporting: Reporting
On detection of an access protection violation the LETH will terminate the access with SRI error that is detected by the XBAR, see SM[HW]:SRI:ERROR_HANDLING.
- ReqIF-WF.Type: Information

###### HTPA-FBBD-GEJA-CGIA_recommendederrorreaction: Recommended error reaction
System integrator to select an appropriate safe reaction in the SMU.
- ReqIF-WF.Type: Information

###### XLZA-FBBD-GEJH-AGED: SM[HW]:LETH:ENDINIT
- IFX.Version: 1
- ReqIF-WF.Type: Heading

###### XLZA-FBBD-GEJH-AGED_description: Description
The LETH provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – LETH (ascending offset address) in the User Manual.
- ReqIF-WF.Type: Information

###### XLZA-FBBD-GEJH-AGED_resetoperationalstate: Reset operational state
An application reset will set the configuration of this safety mechanism back to its default value.
- ReqIF-WF.Type: Information

###### XLZA-FBBD-GEJH-AGED_configurationandactivation: Configuration and activation
This safety mechanism is active after intentional configuration by application software through the PROTE registers.
- ReqIF-WF.Type: Requirement

###### XLZA-FBBD-GEJH-AGED_test: Test
This safety measure can be tested after the PROT owner has been configured:
Write access to a protected register by a master agent function that is not the PROT owner.
- ReqIF-WF.Type: Requirement

###### XLZA-FBBD-GEJH-AGED_reporting: Reporting
On detection of an access protection violation the LETH will terminate the access with SRI error that is detected by the XBAR, see SM[HW]:SRI:ERROR_HANDLING.
- ReqIF-WF.Type: Information

###### XLZA-FBBD-GEJH-AGED_recommendederrorreaction: Recommended error reaction
System integrator to select an appropriate safe reaction in the SMU.
- ReqIF-WF.Type: Information

##### FBBA-FACA-BGCE-EGIA: Alarms
LETH alarms
| Alarm name | Safety mechanism | Alarm flag to be cleared in |
| --- | --- | --- |
| SRI XBAR Bus Error Event Alarm | SM[HW]:LETH:SV_AP SM[HW]:LETH:CFG_AS_AP SM[HW]:LETH:ENDINIT SM[HW]:LETH:SAFETY_ENDINIT | SMU only |
- IFX.Version: 1
- ReqIF-WF.Type: Information

##### EIFA-FAFF-HADF-EBDC: External safety mechanisms
- IFX.Version: 1
- ReqIF-WF.Type: Information

###### TGLA-FBJG-FGBC-BBFC: ESM[SW]:LETH:ISR_MONITOR
This ESM shall detect missing or unintended interrupts originating from the LETH module. Usage of interrupts in this FB depends on the use cases and code implementation.
Transmit / Receive interrupts
The LETH module signals to the application software that a message was received by triggering the interrupt LETH_IR_DMARXy (y = Number of the Rx DMA Channel).
Similarly, a transmitted message is signaled by triggering the interrupt LETH_IR_DMATXy (y = Number of the Tx DMA Channel).
To detect individual missing or unintended transmit or receive interrupts, the system integrator shall use the properties of the safe E2E communication (e.g. timestamp or frame counter). For example, a repeated receive frame counter value indicates that an unintended receive interrupt has occurred. Interrupts missing altogether are covered by the timeout mechanism of the safe E2E communication.
Upon detection of a missing or unintended interrupt, the application software shall trigger an appropriate reaction.
Other interrupts:
Another interrupt originating from the LETH module can be used if the system integrator wishes to do so. This is: LETH_IR_INTR. Errors in the communication due to unintended or missing interrupts of this type are also covered by safe E2E communication.
Unused interrupts:
The application software shall disable any interrupts not being used in the following registers: PORTi_MAC_Interrupt_Enable, DMA_CHi_Interrupt_Enable, Porti_MTL_EST_Intr_Enable, Porti_MTL_RXP_Interrupt_Control_Status, Porti_MTL_Qi_Interrupt_Control_Status, Porti_MAC_PCTW_Intr_Enable, Porti_MAC_PCTH_Intr_Enable, Porti_MMC_Rx_Interrupt_Mask, Porti_MMC_Tx_Interrupt_Mask. Unused interrupts shall also be disabled in the interrupt router SRC register.
- IFX.Version: 5
- ReqIF-WF.Type: Heading

###### TGLA-FBJG-FGBC-BBFC_description: Description
- ReqIF-WF.Type: Requirement

###### UHYA-FBJG-FGCB-AHGG: ESM[SW]:LETH:SAFE_COMMUNICATION
- IFX.Version: 2
- ReqIF-WF.Type: Heading

###### UHYA-FBJG-FGCB-AHGG_description: Description
Random hardware faults in the communication controller or in the communication interface can lead to corruption or loss of safety related data carried by a communication frame. In-order to detect the causes or effects of such communication faults, the application software has to implement safe End-to-End communication protecting the safety critical data.
The Safe End-to-End communication has to be implemented by application software of both the sender and the receiver of a communication frame. The sender appends an "E2E header" containing safety elements such as CRC or Counter to the communication data. The receivers evaluates the safety elements contained in the E2E header of the communication frame in order to detect faults. Figure below shows an example layout and construction of a communication frame protected by Safe End-to-End communication.
Safe End-to-End Communication
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The following section describes the safety elements contained in the E2E header
Cyclic Redundancy Check (CRC)
The CRC is calculated by the sender for the contents of the safety critical communication data. The CRC protects against data corruption. The user is responsible for choosing an appropriate CRC polynomial with sufficient Hamming Distance to provide required error detection capability for a corresponding length of communication data. It is recommended to use a different CRC polynomial1 that the one used by the communication controller (if any) to provide redundancy. The receiver evaluates the CRC in the E2E header of the received communication frame to detect data corruption. A mismatch of the computed CRC value compared to the received CRC value indicates occurrence of data corruption.
1Hint: AUTOSAR Specification of SW-C End-to-End Communication Protection Library Release 4.3.1 recommends CRC polynomials to be used for various length of application data.
Counter
The Counter enables to detect faults such as loss of data, repetition of data. The sender for a given application data, inserts a counter value to the E2E header. The counter value is incremented for every transmission of the application data. The receiver evaluates the counter value in the E2E header of the received communication frame with an expected counter value. The following error scenarios can be detected
- Repetition of frame - The received counter value is the same as that of the previous counter value
- Loss of frame(s) - The received counter value is non–consecutive
The receiver upon successful evaluation of the received communication frame increments the corresponding current counter value.
Note: The user is responsible for implementing counter synchronization methods between the sender and receiver.
The application software can combine the counter value with a timer to detect delayed communication or block in the communication interface. Example: a timer (for example the system timer (STM)) can be configured to trigger a periodic check of the counter value of the associated application data. If the counter value does not change for a given time interval (for example within an FTTI), then delayed communication or block in communication is detected.
- ReqIF-WF.Type: Requirement

#### JCOA-EECH-GCFG-EGDD: Low Latency Interconnect (LLI)
The Low Latency Interconnect (LLI) is an Advanced Microcontroller Bus Architecture (AMBA) sub-system which allows simultaneous transfer between different slaves and different masters of the AMBA (AXI/AHB/APB) sub-system. All masters and slaves connected to the LLI have 32-bit address and data paths and operate on the same clock domain.
- IFX.Version: 1
- ReqIF-WF.Type: Information

##### ZEMA-FAFF-HAFI-BDIJ: Internal safety mechanisms
- IFX.Version: 1
- ReqIF-WF.Type: Information

###### VCFA-EHGC-GJGE-CGGJ: SM[HW]:LLI:TRANSACTION_INTEGRITY
- IFX.Version: 21
- ReqIF-WF.Type: Heading

###### VCFA-EHGC-GJGE-CGGJ_description: Description
The LLI implements ECC and parity mechanisms to ensure transaction integrity between master and slave ports. Parity mechanisms protect the control signals generated by an LLI agent and are checked at the receiving agent. Read and write data is EDC encoded before being sent by an agent. If the checking agent detects an error, an LLI PARITY/ECC decoding alarm is raised, and the source of the alarm is written into the Alarm Event (ALEV) register.
The LLI interconnect ECC encodes the address channels for both reads and writes. An LLI master port ECC encodes the address and control signals which are then checked at the target LLI slave port. If the slave port detects an error, an LLI PARITY/ECC decoding alarm is raised, and the source of the alarm is written into the Alarm Event (ALEV) register.
The LLI interconnect ECC encodes the data channels for both reads and writes. The driving port encodes the data and control signals which are then checked at the target port. If the target port detects an error, an LLI PARITY/ECC decoding alarm is raised, and the source of the alarm is written into the Alarm Event (ALEV) register.
When an AXI path crosses an asynchronous clock domain, a synchronizer is inserted on the path. Since parity on handshake signals cannot be carried over the asynchronous boundary (multi-bit synchronization on handshake signals not permitted by design) the re-sync stage monitors errors on incoming handshake signals on various channels as well as LLI failure modes across the asynchronous boundary. When errors are detected, the re-sync stage relays the error on the outgoing channels by corrupting more than two handshake parity bits thus extending the protection along the asynchronous boundary.
- ReqIF-WF.Type: Information

###### VCFA-EHGC-GJGE-CGGJ_resetoperationalstate: Reset operational state
This safety mechanism and the elements which make it up are active directly after application reset.
- ReqIF-WF.Type: Information

###### VCFA-EHGC-GJGE-CGGJ_configurationandactivation: Configuration and activation
N.A.
- ReqIF-WF.Type: Requirement

###### VCFA-EHGC-GJGE-CGGJ_test: Test
LLI permits fault injection to monitor EDC, parity logic as well as the alarm signaling associated with transaction integrity monitoring on all 5 AXI channels.
Depending on the channel and direction of the signal within that channel, two registers are provided for error injection.
MEGEN: Injects errors on signals that are outputs when seen from a master interface. Examples include, AxADDR and other transaction attributes, WDATA as well as handshake signals such as AWVALID, ARVALID, WVALID, RREADY and BREADY. The full list of possibilities is as available in the register. The designated port to inject errors is the LLI port to which S2L is attached.
SEGEN: Injects errors on signals that are outputs when seen from a slave interface. Examples include, RDATA, BRESP and other response signals, as well as handshake signals such as RVALID, BVALID, ARREADY, AWREADY and WREADY. The full list of possibilities is as available in the register. The designated port to inject slave side errors is the LLI port to which the PPU.SFR is attached.
To use the provided function for testing of the associated safety mechanism, the following sequence of actions are required:
1. Chose the signals on which errors are to be injected by configuring MEGEN or SEGEN
2. Activating transaction: Once setup, generate a transaction which will exercise the signal chosen. For example to inject an error on WVALID, a write transaction is required.
3. Once setup, the immediate next transaction visible on that interface will be considered for error injection. Once an error is injected the corresponding MEGEN, SEGEN configuration bit is cleared. ( Once configured, a register read back is considered as the next transaction, so it could also trigger the mechanism on certain paths)
4. An error injection will cause the sensitized decoder to report an internal alarm which will be captured in the ALEV register and signaled to the SMU
5. The ALEV register as well as the SMU can then be used as an observation mechanism to validate the safety logic is functioning as intended
By directing the activating transaction to different slave ports (or master ports), all decoders can be tested.
- ReqIF-WF.Type: Requirement

###### VCFA-EHGC-GJGE-CGGJ_reporting: Reporting
On detection of an ECC or parity violation the SMM updates the Alarm Event register with the source of the alarm, and signals an LLI PARITY/ECC decoding alarm to the SMU.
- ReqIF-WF.Type: Information

###### VCFA-EHGC-GJGE-CGGJ_recommendederrorreaction: Recommended error reaction
System integrator to select appropriate safe reaction in SMU.
- ReqIF-WF.Type: Information

###### IXBA-EHHJ-GDCG-GFAI: SM[HW]:LLI:ERROR_HANDLING
- IFX.Version: 1
- ReqIF-WF.Type: Heading

###### IXBA-EHHJ-GDCG-GFAI_description: Description
If a slave error or decode error is detected in the LLI, the master receiving the error raises an alarm or an exception.
- ReqIF-WF.Type: Information

###### IXBA-EHHJ-GDCG-GFAI_resetoperationalstate: Reset operational state
The safety mechanism is active directly after application reset.
- ReqIF-WF.Type: Information

###### IXBA-EHHJ-GDCG-GFAI_configurationandactivation: Configuration and activation
N.A.
- ReqIF-WF.Type: Requirement

###### IXBA-EHHJ-GDCG-GFAI_test: Test
This safety
mechanism can be tested by reading from a register location where no
register is located within valid register space.
- ReqIF-WF.Type: Requirement

###### IXBA-EHHJ-GDCG-GFAI_reporting: Reporting
On detection of an error the SMM signals bus error to the AXI interconnect will go to the originating master, which will further raise an alarm to the SMU or generate an exception. The error can be detected in three different locations depending on the source and type of the transaction:
- Read transactions via the S2L - any read error is detected by the XBAR connected to the S2L, see SM[HW]:SRI:ERROR_HANDLING
- Writes transactions via the S2L - any write error is detected by the S2L, and an S2L data phase error alarm is sent to the SMU
- Transactions via the PPU - the error is detected by the PPU, which raises an exception
- ReqIF-WF.Type: Information

###### IXBA-EHHJ-GDCG-GFAI_recommendederrorreaction: Recommended error reaction
System integrator to select appropriate safe reaction in SMU or PPU.
- ReqIF-WF.Type: Information

###### XPZA-EHHH-CJIG-JIFG: SM[HW]:LLI:ADDRESS_MAP_MONITORING
For the S2L master interface write path, an alarm will be raised by the S2L, but for the read path the alarm will be raised by the XBAR connecting to the S2L. For the PPU master interface, the PPU will raise an internal exception.
- IFX.Version: 1
- ReqIF-WF.Type: Heading

###### XPZA-EHHH-CJIG-JIFG_description: Description
Each LLI slave interface implements a mechanism to check that the address forwarded to it is within the expected range. If the address is not in the expected range, the slave interface responds with a slave error, which the interconnect forwards to the originating master interface.
- ReqIF-WF.Type: Information

###### XPZA-EHHH-CJIG-JIFG_resetoperationalstate: Reset operational state
The safety mechanism is active directly after application reset.
- ReqIF-WF.Type: Information

###### XPZA-EHHH-CJIG-JIFG_configurationandactivation: Configuration and activation
N.A.
- ReqIF-WF.Type: Requirement

###### XPZA-EHHH-CJIG-JIFG_test: Test
N.A.
- ReqIF-WF.Type: Requirement

###### XPZA-EHHH-CJIG-JIFG_reporting: Reporting
On detection of an address outside of the expected range the LLI will terminate the access with an LLI slave error that is detected by the originating master, see SM[HW]:LLI:ERROR_HANDLING.
- ReqIF-WF.Type: Information

###### XPZA-EHHH-CJIG-JIFG_recommendederrorreaction: Recommended error reaction
System integrator to select appropriate safe reaction in SMU or PPU.
- ReqIF-WF.Type: Information

###### IRLA-EHHA-DJCG-IEJH: SM[HW]:LLI:SV_AP
On detection of a supervisor privilege violation the LLI will terminate the access with an LLI slave error that is detected by the originating master, see SM[HW]:LLI:ERROR_HANDLING.
System integrator to select an appropriate safe reaction in the SMU or PPU.
- IFX.Version: 5 5
- ReqIF-WF.Type: Heading

###### IRLA-EHHA-DJCG-IEJH_description: Description
Critical module registers are implemented with a write access restriction that allows access only to masters with supervisor (SV) mode privilege.
Unauthorized access attempts are blocked by this mechanism.
For a list of the registers protected by SV, see tables Register overview – access mode glossary and Register overview – LLI (ascending offset address) in the User Manual.
- ReqIF-WF.Type: Information

###### IRLA-EHHA-DJCG-IEJH_resetoperationalstate: Reset operational state
The safety mechanism is active after application reset.
- ReqIF-WF.Type: Information

###### IRLA-EHHA-DJCG-IEJH_configurationandactivation: Configuration and activation
N.A.
- ReqIF-WF.Type: Requirement

###### IRLA-EHHA-DJCG-IEJH_test: Test
This safety
measure can be tested by an write access to a protected register by
a master agent function without
supervisor
(SV) access rights.
- ReqIF-WF.Type: Requirement

###### IRLA-EHHA-DJCG-IEJH_reporting: Reporting
- ReqIF-WF.Type: Information

###### IRLA-EHHA-DJCG-IEJH_recommendederrorreaction: Recommended error reaction
- ReqIF-WF.Type: Information

###### BXXA-EHHJ-GGBG-ADJI: SM[HW]:LLI:CFG_AS_AP
On detection of an access protection violation the LLI terminates the access with an error LLI slave error, see SM[HW]:LLI:ERROR_HANDLING.
System integrator to select an appropriate safe reaction in the SMU or PPU.
- IFX.Version: 1 1
- ReqIF-WF.Type: Heading

###### BXXA-EHHJ-GGBG-ADJI_description: Description
The LLI checks if the access master agent function identifier is enabled for the type of access (read access and write access, configured through the LLI ACCEN registers) to the selected register.
Unauthorized access attempts are blocked by this mechanism.
- ReqIF-WF.Type: Information

###### BXXA-EHHJ-GGBG-ADJI_resetoperationalstate: Reset operational state
An application reset will set the configuration of this safety mechanism back to its default value.
- ReqIF-WF.Type: Information

###### BXXA-EHHJ-GGBG-ADJI_configurationandactivation: Configuration and activation
This safety mechanism is active after intentional configuration by application software through the ACCENx registers.
- ReqIF-WF.Type: Requirement

###### BXXA-EHHJ-GGBG-ADJI_test: Test
- ReqIF-WF.Type: Requirement

###### BXXA-EHHJ-GGBG-ADJI_section5
This safety measure can be tested after the ACCENx has been configured:
Write access to a protected register by a master agent function that is not the ACCEN owner.
- ReqIF-WF.Type: Information

###### BXXA-EHHJ-GGBG-ADJI_reporting: Reporting
- ReqIF-WF.Type: Information

###### BXXA-EHHJ-GGBG-ADJI_recommendederrorreaction: Recommended error reaction
- ReqIF-WF.Type: Information

##### IMJA-EHBJ-DJEJ-EEEI: Alarms
LLI alarms
| Alarm name | Safety mechanism | Alarm flag to be cleared in |
| --- | --- | --- |
| LLI PARITY/ECC decoding alarm | SM[HW]:LLI:TRANSACTION_INTEGRITY | SMU only |
| LLI PARITY/ECC decoding alarm | SM[HW]:LLI:ERROR_HANDLING | SMU only |
- IFX.Version: 1
- ReqIF-WF.Type: Information

##### XJGA-FAFF-HAFI-HCCH: External safety mechanisms
- IFX.Version: 1
- ReqIF-WF.Type: Information

#### KFNA-EDEA-CGIJ-FHAG: Logic-Test (TRI)
The LBIST (Logic Built-In Self Test) is an on-chip hardware mechanism that can be used to detect latent faults in the microcontroller. The LBIST implementation in the AURIX™TC4xx platform allows the execution of periodic self-tests of the microcontroller logic. It is accessed through registers in the test register interface (TRI) unit.
- ReqIF-WF.Type: Information

##### ICUA-FAFF-HBDF-EHEE: Internal safety mechanisms
- IFX.Version: 1
- ReqIF-WF.Type: Information

###### YQGA-EHEI-AHIB-GFAJ: SM[HW]:MCU:LBIST
- IFX.Version: 1
- ReqIF-WF.Type: Heading

###### YQGA-EHEI-AHIB-GFAJ_description: Description
LBIST is an AURIX™ 3rd Generation platform safety mechanism which is based on an automatic structural system-test method. It checks the MCU digital logic for Hard Errors: latent and multi-point faults. The SM[HW]:MCU:LBIST is focusing exclusively on latent and multi-point faults within functional safety hardware structures. Its reduced volume allows a significant faster execution compared to SM[HW]:MCU:LBIST_COMPLETE.
A successful LBIST operation is indicated through a DONE signal in the LBIST_STAT_TEST register and an unique signature for each hierarchical domain in the LBIST_STAT_RESx_SIG register. Errors in the LBIST operation are detected by comparison of the signature result and the expected signature values which are stored in flash. A full description of the LBIST functionality is given in the Logic-Test (TRI) chapter of user manual ("Functional description" and "Registers" sections).
Due to the hierarchical scan architecture of AURIX™ 3rd Generation platform LBIST is configured and started independently for different hierarchical scan domains of the device (in total up to 8 scan hierarchies are implemented). All data contents within the logic device registers will be deleted during this test.
In case a LBIST procedure is triggered in any hierarchical domain, the whole chip is brought into a specific scan-test, during which no functional operation is possible any more. Consequently all GPIOs of the chip will be automatically forced to a static reset state (input pull-up or tri-state according to configuration) as long as the LBIST execution is underway. Steering of the LBIST procedure is handled by a central LBIST controller inside of TRI. It supervises local LBIST controller satellites, which handle the scan shift and capture sequencing in each hierarchical domain.
LBIST is protected from two aspects:
1. Safe execution: If triggered during boot or at a later point during application LBIST must execute in a reliable way and bring the device back to a reset state after execution is finished
2. Freedom from interference: All the LBIST hardware components shall reside in a safe idle state, which do not disturb the device's functionality, until they are triggered
To address unintended LBIST execution failure mode, the redundant LBIST request bit is implemented in the LBIST_CTRL_REQ register. In order to start an LBIST operation the LBIST_CTRL_REQ.LBISTREQ and LBIST_CTRL_REQ.LBISTREQRED bits must both be written high.
- ReqIF-WF.Type: Information

###### YQGA-EHEI-AHIB-GFAJ_resetoperationalstate: Reset operational state
A cold power-on reset will set the configuration of this safety mechanism back to its default value.
- ReqIF-WF.Type: Information

###### YQGA-EHEI-AHIB-GFAJ_configurationandactivation: Configuration and activation
Please refer to ESM[SW]:MCU:LBIST.
- ReqIF-WF.Type: Requirement

###### YQGA-EHEI-AHIB-GFAJ_test: Test
Dedicated alarm signals are implemented which indicate an erroneous activation of LBIST (LBIST alarm) or test mode (test mode alarm). It is recommended to check the LBIST and test mode alarm signals for their correct functionality by error injection once per driving cycle. For this purpose the LBIST_CTRL_REQ.ERRINJ bit is provided, which will inject a SMU alarm on LBIST alarm and test mode alarm if written with a '1' value. This check can be done at any time before or after LBIST execution.
- ReqIF-WF.Type: Requirement

###### YQGA-EHEI-AHIB-GFAJ_reporting: Reporting
LBIST alarm: This alarm signal will be activated if the LBIST state machine is not in the Reset or Idle state, or if some global LBIST enable signals are active. Consequently the LBIST alarm signal is always active during LBIST execution. And also afterward until the LBIST controller is set back to its idle state through LBIST_CTRL_REQ.RESET
- ReqIF-WF.Type: Information

###### YQGA-EHEI-AHIB-GFAJ_recommendederrorreaction: Recommended error reaction
System integrator to select an appropriate safe reaction in the SMU.
- ReqIF-WF.Type: Information

###### NKNA-FCIG-BGJC-HFFJ: SM[HW]:MCU:LBIST_COMPLETE
- IFX.Version: 1
- ReqIF-WF.Type: Heading

###### NKNA-FCIG-BGJC-HFFJ_description: Description
LBIST is an AURIX™ 3rd Generation platform safety mechanism which is based on an automatic structural system-test method. It checks the MCU digital logic for Hard Errors: latent and multi-point faults. The SM[HW]:MCU:LBIST_COMPLETE is targeting latent faults and multi-point faults within functional safety hardware structures. It is applicable for safety relevant modules which cannot isolate their functional safety hardware structures and have to be tested as a whole. In contrary to SM[HW]:MCU:LBIST its execution time is significantly higher.
A successful LBIST operation is indicated through a DONE signal in the LBIST_STAT_TEST register and an unique signature for each hierarchical domain in the LBIST_STAT_RESx_SIG register. Errors in the LBIST operation are detected by comparison of the signature result and the expected signature values which are stored in flash. A full description of the LBIST functionality is given in the Logic-Test (TRI) chapter of user manual ("Functional description" and "Registers" sections).
Due to the hierarchical scan architecture of AURIX™ 3rd Generation platform LBIST is configured and started independently for different hierarchical scan domains of the device (in total up to 8 scan hierarchies are implemented). All data contents within the logic device registers will be deleted during this test.
In case a LBIST procedure is triggered in any hierarchical domain, the whole chip is brought into a specific scan-test, during which no functional operation is possible any more. Consequently all GPIOs of the chip will be automatically forced to a static reset state (input pull-up or tri-state according to configuration) as long as the LBIST execution is underway. Steering of the LBIST procedure is handled by a central LBIST controller inside of TRI. It supervises local LBIST controller satellites, which handle the scan shift and capture sequencing in each hierarchical domain.
LBIST is protected from two aspects:
1. Safe execution: If triggered during boot or at a later point during application LBIST must execute in a reliable way and bring the device back to a reset state after execution is finished
2. Freedom from interference: All the LBIST hardware components shall reside in a safe idle state, which do not disturb the device's functionality, until they are triggered
To address unintended LBIST execution failure mode, the redundant LBIST request bit is implemented in the LBIST_CTRL_REQ register. In order to start an LBIST operation the LBIST_CTRL_REQ.LBISTREQ and LBIST_CTRL_REQ.LBISTREQRED bits must both be written high.
- ReqIF-WF.Type: Information

###### NKNA-FCIG-BGJC-HFFJ_resetoperationalstate: Reset operational state
A cold power-on reset will set the configuration of this safety mechanism back to its default value.
- ReqIF-WF.Type: Information

###### NKNA-FCIG-BGJC-HFFJ_configurationandactivation: Configuration and activation
Please refer to ESM[SW]:MCU:LBIST.
- ReqIF-WF.Type: Requirement

###### NKNA-FCIG-BGJC-HFFJ_test: Test
Dedicated alarm signals are implemented which indicate an erroneous activation of LBIST (LBIST alarm) or test mode (test mode alarm). It is recommended to check the LBIST and test mode alarm signals for their correct functionality by error injection once per driving cycle. For this purpose the LBIST_CTRL_REQ.ERRINJ bit is provided, which will inject a SMU alarm on LBIST alarm and test mode alarm if written with a '1' value. This check can be done at any time before or after LBIST execution.
- ReqIF-WF.Type: Requirement

###### NKNA-FCIG-BGJC-HFFJ_reporting: Reporting
LBIST alarm: This alarm signal will be activated if the LBIST state machine is not in the Reset or Idle state, or if some global LBIST enable signals are active. Consequently the LBIST alarm signal is always active during LBIST execution. And also afterward until the LBIST controller is set back to its idle state through LBIST_CTRL_REQ.RESET
- ReqIF-WF.Type: Information

###### NKNA-FCIG-BGJC-HFFJ_recommendederrorreaction: Recommended error reaction
System integrator to select an appropriate safe reaction in the SMU.
- ReqIF-WF.Type: Information

###### QVVA-EHHJ-FDCC-DJCD: SM[HW]:DFT:ENDINIT
- IFX.Version: 1 1
- ReqIF-WF.Type: Heading

###### QVVA-EHHJ-FDCC-DJCD_description: Description
The DFT provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – DFT (ascending offset address) in the User Manual.
- ReqIF-WF.Type: Information

###### QVVA-EHHJ-FDCC-DJCD_resetoperationalstate: Reset operational state
An application reset will set the configuration of this safety mechanism back to its default value.
- ReqIF-WF.Type: Information

###### QVVA-EHHJ-FDCC-DJCD_configurationandactivation: Configuration and activation
This safety mechanism is active after intentional configuration by application software through the PROTE register.
- ReqIF-WF.Type: Requirement

###### QVVA-EHHJ-FDCC-DJCD_test: Test
This safety measure can be tested after the PROT owner has been configured:
Write access to a protected register by a master agent function that is not the PROT owner.
- ReqIF-WF.Type: Requirement

###### QVVA-EHHJ-FDCC-DJCD_reporting: Reporting
On detection of an access protection violation the DFT will terminate the access with FPI error that is detected by the BCU, see SM[HW]:FPI:ERROR_HANDLING.
- ReqIF-WF.Type: Information

###### QVVA-EHHJ-FDCC-DJCD_recommendederrorreaction: Recommended error reaction
System integrator to select an appropriate safe reaction in the SMU.
- ReqIF-WF.Type: Information

###### RURA-EHHJ-FDCC-EBDG: SM[HW]:DFT:SAFETY_ENDINIT
- IFX.Version: 8 8
- ReqIF-WF.Type: Heading

###### RURA-EHHJ-FDCC-EBDG_description: Description
The DFT provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – DFT (ascending offset address) in the User Manual.
- ReqIF-WF.Type: Information

###### RURA-EHHJ-FDCC-EBDG_resetoperationalstate: Reset operational state
An application reset will set the configuration of this safety mechanism back to its default value.
- ReqIF-WF.Type: Information

###### RURA-EHHJ-FDCC-EBDG_configurationandactivation: Configuration and activation
This safety mechanism is active after intentional configuration by application software through the PROTSE register.
- ReqIF-WF.Type: Requirement

###### RURA-EHHJ-FDCC-EBDG_test: Test
This safety measure can be tested after the PROT owner has been configured:
Write access to a protected register by a master agent function that is not the PROT owner.
- ReqIF-WF.Type: Requirement

###### RURA-EHHJ-FDCC-EBDG_reporting: Reporting
On detection of an access protection violation the DFT will terminate the access with FPI error that is detected by the BCU, see SM[HW]:FPI:ERROR_HANDLING.
- ReqIF-WF.Type: Information

###### RURA-EHHJ-FDCC-EBDG_recommendederrorreaction: Recommended error reaction
System integrator to select an appropriate safe reaction in the SMU.
- ReqIF-WF.Type: Information

###### BVFA-EHHJ-FDCC-DFEI: SM[HW]:DFT:CFG_AS_AP
- IFX.Version: 1 1
- ReqIF-WF.Type: Heading

###### BVFA-EHHJ-FDCC-DFEI_description: Description
The DFT checks if the access master agent function identifier is enabled for the type of access (read access and write access, configured through the DFT ACCEN registers) to the selected register.
Unauthorized access attempts are blocked by this mechanism.
- ReqIF-WF.Type: Information

###### BVFA-EHHJ-FDCC-DFEI_resetoperationalstate: Reset operational state
An application reset will set the configuration of this safety mechanism back to its default value.
- ReqIF-WF.Type: Information

###### BVFA-EHHJ-FDCC-DFEI_configurationandactivation: Configuration and activation
This safety mechanism is active after intentional configuration by application software through the ACCENx registers.
- ReqIF-WF.Type: Requirement

###### BVFA-EHHJ-FDCC-DFEI_test: Test
This safety measure can be tested after the ACCENx has been configured:
Write access to a protected register by a master agent function that is not the ACCEN owner.
- ReqIF-WF.Type: Requirement

###### BVFA-EHHJ-FDCC-DFEI_reporting: Reporting
On detection of an access protection violation the DFT will terminate the access with FPI error that is detected by the BCU, see SM[HW]:FPI:ERROR_HANDLING.
- ReqIF-WF.Type: Information

###### BVFA-EHHJ-FDCC-DFEI_recommendederrorreaction: Recommended error reaction
System integrator to select an appropriate safe reaction in the SMU.
- ReqIF-WF.Type: Information

###### SVLA-EHHJ-FDCC-AFEE: SM[HW]:DFT:SV_AP
- IFX.Version: 1 1
- ReqIF-WF.Type: Heading

###### SVLA-EHHJ-FDCC-AFEE_description: Description
Critical module registers are implemented with a write access restriction that allows access only to masters with supervisor (SV) mode privilege.
Unauthorized access attempts are blocked by this mechanism.
For a list of the registers protected by SV, see tables Register overview – access mode glossary and Register overview – DFT (ascending offset address) in the User Manual.
- ReqIF-WF.Type: Information

###### SVLA-EHHJ-FDCC-AFEE_resetoperationalstate: Reset operational state
The safety mechanism is active after application reset.
- ReqIF-WF.Type: Information

###### SVLA-EHHJ-FDCC-AFEE_configurationandactivation: Configuration and activation
N.A.
- ReqIF-WF.Type: Requirement

###### SVLA-EHHJ-FDCC-AFEE_test: Test
This safety measure can be tested by a write access to a protected register by a master agent function without supervisor (SV) access rights.
- ReqIF-WF.Type: Requirement

###### SVLA-EHHJ-FDCC-AFEE_reporting: Reporting
On detection of an access protection violation the DFT will terminate the access with FPI error that is detected by the BCU, see SM[HW]:FPI:ERROR_HANDLING.
- ReqIF-WF.Type: Information

###### SVLA-EHHJ-FDCC-AFEE_recommendederrorreaction: Recommended error reaction
System integrator to select an appropriate safe reaction in the SMU.
- ReqIF-WF.Type: Information

###### XNJA-EHFA-GBCD-DJFB: SM[HW]:DFT:FFI_CONTROL
- IFX.Version: 15
- ReqIF-WF.Type: Heading

###### XNJA-EHFA-GBCD-DJFB_description: Description
Freedom from interference for general test overruling:
DFT-FB controls several signals which allow a direct overruling of basic system functionality (involving Clocks, Reset and Port-logic) for test purpose only. When a safe application is underway, it has to be ensured that within the DFT block, at the source side these signals always stay at their inactive state (safe value) to ensure freedom-from-interference. Due to the fact that the test-related overruling signals are widely spread across the chip area additional blocking mechanisms are also implemented on the destination side for safety-critical test overruling signals (failure rate reduction). The blocking is realized through simple AND-gating which involves the test-override signal and combines it with a general test-enable signal. This ensures that the resulting test control override signal always remains at its inactive state as long the chip is not operating in a specific test-mode.
The above described gating mechanism is mainly realized by pre-determined "test mode activity indicator" signals (originated by Test Control Unit (TCU)) to ensure freedom of interference. In addition to gating, all signals used to safeguard safety-critical signals are monitored to detect whether they become latent.
Freedom from Interference for Test Reset:
DFT generates three kinds of resets, scan reset, system reset and internal PORST reset. All those resets are blocked with a gating mechanism to prevent unintended reset triggering.
- ReqIF-WF.Type: Information

###### XNJA-EHFA-GBCD-DJFB_resetoperationalstate: Reset operational state
The safety mechanism is active after application reset.
- ReqIF-WF.Type: Information

###### XNJA-EHFA-GBCD-DJFB_configurationandactivation: Configuration and activation
N.A.
- ReqIF-WF.Type: Requirement

###### XNJA-EHFA-GBCD-DJFB_test: Test
The application software can trigger the Test mode alarm to SMU through error injection. For that purpose LBIST provides the single control bit field ERRINJ in the LBIST_CTRL_REQ register.
- ReqIF-WF.Type: Requirement

###### XNJA-EHFA-GBCD-DJFB_reporting: Reporting
If any of the "test mode activity indicator" signals, is unintentionally activated in user application mode, test mode alarm will be reported.
Test mode alarm: This alarm signal is activated if any of the Test Control Units (TCUs) general test-mode enabling signals are in unintended active state. Consequently the Test mode alarm signal is always active if the microcontroller is operating in general test mode
- ReqIF-WF.Type: Information

###### XNJA-EHFA-GBCD-DJFB_recommendederrorreaction: Recommended error reaction
System integrator to select an appropriate safe reaction in the SMU.
- ReqIF-WF.Type: Information

##### HHRA-EHBJ-DHBC-JCFB: Alarms
TRI alarms
| Alarm name | Safety mechanism | Alarm flag to be cleared in |
| --- | --- | --- |
| Test mode alarm | SM[HW]:DFT:FFI_CONTROL | SMU only |
| LBIST alarm | SM[HW]:MCU:LBIST | SMU only |
| FPI error alarm | SM[HW]:DFT:SV_AP SM[HW]:DFT:CFG_AS_AP SM[HW]:DFT:ENDINIT SM[HW]:DFT:SAFETY_ENDINIT | SMU only |
- IFX.Version: 1
- ReqIF-WF.Type: Information

##### WNAA-FAFF-HBDG-JAFI: External safety mechanisms
- IFX.Version: 1
- ReqIF-WF.Type: Information

###### UVIA-EHEI-AIJA-CABH: ESM[SW]:MCU:LBIST
- IFX.Version: 19
- ReqIF-WF.Type: Heading

###### UVIA-EHEI-AIJA-CABH_description: Description
LBIST can be triggered automatically through the firmware after a cold power-on reset if this is configured in the UCB. If not triggered automatically it has to be configured and started through the Application SW by using the LBIST_CTRL_... registers as described in the user manual Logic-Test (TRI) chapter ("Functional description" and "Registers" sections).
The Application SW shall configure LBIST parameters via LBIST_CTRL_CFGA and start LBIST execution via LBIST_CTRL_REQ according to the description provided in the user manual (see "Functional description" and "Registers" sections).
Different LBIST scenarios are supported as described in the user manual Logic-Test (TRI) chapter "LBIST Application Scenarios" section: Specifically for key-on scenarios only those flip-flops which are part of safety mechanisms can be included into LBIST test (safety LBIST). This reduces the power consumption and allows faster LBIST execution. For key-off scenarios LBIST can also be started on all flip-flops of each hierarchical scan domain (full LBIST).
Init Configuration:
As a default LBIST_CTRL_CFGA - LBIST_CTRL_CFGF register will be pre-loaded by FW with a "key-on" scenario configuration allowing to perform LBIST test on all functional safety hardware mechanisms for detection of latent faults within 5-6 ms. In order to use the default configuration Application SW shall just write LBIST_CTRL_REQ.LBISTREQ and LBIST_CTRL_REQ.LBISTREQRED bits to high. After LBIST has been finished a new LBIST run can only be started after a POWER_ON_RESET or if central LBIST controller has been set back to its idle state via LBIST_CTRL_REQ.RESET function.
LBIST Result Extraction:
The Application SW shall check the LBIST results and compare it with the expected value after LBIST execution is finished.
Before checking the MISR signature the Application SW shall verify if the previously triggered LBIST run terminated successfully by checking if LBIST_STAT_TEST.DONE='1' and CLDRSTRIG.LBTERM='1' (CLDRSTRIG register is located in PMS). In addition to this Application SW shall check the LBIST_STAT_TEST register's DOMDONE0-DOMDONE7 bit to see if LBIST has been executed for the requested hierarchical domains.
Application SW shall also read the LBIST_STAT_TEST register's KEYIND and SAFEIND bits to recognize the type of executed LBIST run. Afterward the 32-bit MISR signature result from each hierarchical domain in LBIST_STAT_RESx_SIG.SIGNATURE (x=domain index) shall be compared with the expected MISR result.
In this conjunction it shall be regarded that the expected MISR signature results are depending on the product version, the number of applied LBIST patterns (LBIST_CTRL_CFGA.PATTERNS) and the SAFESEL LBIST config bit in LBIST_CTRL_CFGA register. For a successful LBIST execution it is essential that the pre-loaded LENGTH/SLENTH values in LBIST_CTRL_CFGB- LBIST_CTRL_CFGE and the contents in LBIST_CTRL_CFGF has not been modified by the Application SW.
Recommendations:
After LBIST termination and evaluation of the MISR signature results it is recommended to bring the LBIST controller to a safe reset-state by setting LBIST_CTRL_REQ.RESET='1'. This will clear the MISR signature in LBIST_STAT_RESx_SIG registers. It is also necessary to de-assert the LBIST alarm.
Additional information on the LBIST software interface can be referenced in the user manual Logic-Test (TRI) chapter "LBIST Configuration Options" and "Registers" section.
It shall be regarded that LBIST is a structural test method which is causing a high switching activity and requires stable environmental voltage and temperature conditions. Therefore it might happen that under extreme operation conditions a single LBIST run might fail by showing an unexpected MISR result.
In this case the faulty silicon behavior shall be confirmed by repeating the LBIST execution at least 2 times.
The number of failing LBIST execution can be stored via the LBIST_CTRL_REQ.FAILCIN field when starting LBIST execution. After LBIST execution the stored value can be retrieved through the LBIST_STAT_TEST.FAILCOUT field. If the LBIST function should fail to produce a correct MISR signature within 3 consecutive runs, the device has to be considered as defect and shall not boot into a safe application.
- ReqIF-WF.Type: Requirement

#### BGDA-FEJI-EHAG-DJJA: Non-Volatile Memory with RRAM (NVMR)
This sub-system provides non-volatile memory for code and data. The memory is divided into separate Program NVM (PNVM) banks to allow parallel read operations and read-while-write functions. For frequent data updates there is a Data NVM (DNVM) memory region available, which allows a high number of program cycles, which is typical of an EEPROM.
The NVMR also provides User Configuration Blocks (UCB) where System and NVMR configuration settings can be stored. For start-up the NVMR also contains a BootROM to store the start-up software.
- IFX.Version: 1
- ReqIF-WF.Type: Information

##### VJEA-FEJI-EHIC-IEID: Internal safety mechanisms
- IFX.Version: 1
- ReqIF-WF.Type: Information

###### WFHA-FDII-CJGH-FCAE: SM[HW]:NVMR:BOOTROM_ADDR_PROTECTION
- IFX.Version: 1
- ReqIF-WF.Type: Heading

###### WFHA-FDII-CJGH-FCAE_description: Description
This safety mechanism will detect address faults in the BootROM decoder.
The BootROM is split into two ROM arrays,each with their own decoder. On a BootROM read access, each ROM array delivers half of the read data (data bits and ECC bits). The SM[HW]:NVMR:BOOTROM_ERROR_CORRECTION checks the validity of the data by using all ECC bits of both arrays. If one of the decoder was delivering a wrong half word, then the probability is high that data and ECC bits will not match.
- ReqIF-WF.Type: Information

###### WFHA-FDII-CJGH-FCAE_resetoperationalstate: Reset operational state
This safety mechanism is active directly after
application reset.
- ReqIF-WF.Type: Information

###### WFHA-FDII-CJGH-FCAE_configurationandactivation: Configuration and activation
N.A.
- ReqIF-WF.Type: Requirement

###### WFHA-FDII-CJGH-FCAE_test: Test
This safety
mechanism has no special test features.
- ReqIF-WF.Type: Requirement

###### WFHA-FDII-CJGH-FCAE_reporting: Reporting
An alarm is generated on detection of a fault in the address decoder of the BootROM.
Alarms
| Alarm name | Alarm interface | Alarm type |
| --- | --- | --- |
| NVMR SRI Address Phase EDC Error | SRI Bus Error Event | Level alarm |
- ReqIF-WF.Type: Information

###### WFHA-FDII-CJGH-FCAE_recommendederrorreaction: Recommended error reaction
The
system integrator
is
to select appropriate safe reaction
in
the SMU.
- ReqIF-WF.Type: Information

###### PFGA-FDII-CAIJ-EBBD: SM[HW]:NVMR:BOOTROM_ERROR_CORRECTION
- IFX.Version: 7
- ReqIF-WF.Type: Heading

###### PFGA-FDII-CAIJ-EBBD_description: Description
This safety mechanism checks for errors in the BootROM read data resulting from faults in the content.
The BootROM stores data with Error Correcting Codes (ECC) in order to protect against data corruption. Data in BootROM uses an ECC code with single bit error correction and double bit error detection (SEC-DED) capabilities.
- ReqIF-WF.Type: Information

###### PFGA-FDII-CAIJ-EBBD_resetoperationalstate: Reset operational state
This safety mechanism is active directly after application reset.
- ReqIF-WF.Type: Information

###### PFGA-FDII-CAIJ-EBBD_configurationandactivation: Configuration and activation
The error correction can be enabled or disabled by a register part of VMT.
- ReqIF-WF.Type: Requirement

###### PFGA-FDII-CAIJ-EBBD_test: Test
N.A.
- ReqIF-WF.Type: Requirement

###### PFGA-FDII-CAIJ-EBBD_reporting: Reporting
Upon the detection of a fault in the read data of the BootROM an alarm is generated.
- ReqIF-WF.Type: Information

###### PFGA-FDII-CAIJ-EBBD_recommendederrorreaction: Recommended error reaction
System integrator to select appropriate safe reaction in SMU.
- ReqIF-WF.Type: Information

###### TLRA-FDII-CCJE-JDHG: SM[HW]:NVMR:MISR
- IFX.Version: 7
- ReqIF-WF.Type: Heading

###### TLRA-FDII-CCJE-JDHG_description: Description
This safety mechanism monitors continuously the RRAM configurations stored in register banks (SFR read and write settings, and wordline redundancy). The RRAM configurations are checked continuously preventing the faults from becoming latent.
Kind of fault detected by this safety mechanism:
- This safety mechanism will detect a fault in the RRAM configuration while MCU run-time
- This safety mechanism will detect, after MCU boot, a fault in the values installed while MCU boot
The monitoring is realized using several instances of an 8 bit multiple input signature register (MISR) calculating cyclically a unique polynomial signature over the register bank entries.
- ReqIF-WF.Type: Information

###### TLRA-FDII-CCJE-JDHG_resetoperationalrate: Reset operational rate
Available in read mode after application reset.
- ReqIF-WF.Type: Information

###### TLRA-FDII-CCJE-JDHG_configurationandactivation: Configuration and activation
This safety mechanism is always active while the RRAM is in read mode meaning after MCU boot, while no RRAM operation is running (visible in the PMURx_UR_REQSTAT.BUSY and DMURx_UR_REQSTAT.BUSY register).
It is recommended to do a first check of the alarms directly after MCU boot to detect faults due to the installation of wrong values.
During run-time the alarm will indicate a flip within the configuration registers.
Note: The safety mechanism needs a continuous time of 100us, where NVMR is in read mode and not in operation mode (indicated by BUSY='1'), to execute in the background.
- ReqIF-WF.Type: Requirement

###### TLRA-FDII-CCJE-JDHG_test: Test
For application software development and alarm lines testing, it is possible to trigger an alarm using PMURx_UR_NVMCON3 .MISRERRINJ without impact on the mission logic.
Note: This is only possible for the PMUR alarms.
- ReqIF-WF.Type: Requirement

###### TLRA-FDII-CCJE-JDHG_reportingrecommendederrorreaction: ReportingRecommended error reaction
An alarm is generated if the polynomial calculation is not matching the expected signature.
An alarm directly after MCU boot indicates that a wrong value of a configuration register for the RRAM read or write has been installed so that a reliable operation might not be possible from the affected memory region. A system reset can be done to repeat the MCU boot but if the problem persists then this RRAM region cannot be used.
If the alarm occurs during run-time then this is an indication of a register flip and might be corrected by an application reset and subsequent MCU boot.
- ReqIF-WF.Type: Information

###### KMSA-FDII-CCIH-IGBE: SM[HW]:NVMR:PNVM_ECC_ONLINE_MONITOR
- IFX.Version: 12
- ReqIF-WF.Type: Heading

###### KMSA-FDII-CCIH-IGBE_description: Description
The PRRAM stores data with Error Correcting Codes (ECC) in order to protect the read data and address against corruption. The PRRAM ECC has the ability to detect and correct located '6-bit group' errors (erasure error) and unlocated '6-bit group' errors (bit-flip error).
The correction logic could as well corrupt data by performing a wrong correction. To detect this fault, the safety mechanism continuously calculates a syndrome out of the corrected word and checks if the syndrome belongs to the error correction codes.
The PRRAM ECC calculates the syndrome in a first stage to detect faults in the read data and address. If the fault can be corrected in the data word, the correction is applied on the data word (data_o). Otherwise a uncorrectable error (err_ucerr) is observed.
To detect faults in the PRRAM ECC logic, the safety mechanism calculates the syndrome on the corrected word in a second stage. If a fault is observed an alarm is sent to the gating logic.
PRRAM ECC online monitor
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The gating logic makes sure that an alarm is sent to the system in these relevant cases only:
- when no uncorrectable error (err_ucerr = 0 B) occurred while reading from the system and the PRRAM ECC online monitor detects an error in the corrected data
- when the error correction is disabled and any error is detected in the data
Note: A uncorrectable error will be noted by the UBAB address buffer of SM[HW]:NVMR:PNVM_ERROR_MANAGEMENT
- ReqIF-WF.Type: Information

###### KMSA-FDII-CCIH-IGBE_resetoperationalstate: Reset operational state
This safety mechanism is active after application reset.
- ReqIF-WF.Type: Information

###### KMSA-FDII-CCIH-IGBE_configurationandactivation: Configuration and activation
The safety mechanism is theoretically active directly after application reset but can only be used once a read on the PRRAM is possible, meaning once the MCU boot process has installed the necessary read conditions.
The prerequisites for the good functioning of this safety mechanism are:
- The software shall enable the ECC correction by keeping PMURx_UR_NVMCON2.ECCCORDIS = 0 B (default reset value)
- The software shall not evaluate the alarm of the online checker if PMURx_UR_NVMCON2.ECCCORDIS = 1 B, because then false positive alarms could be generated
- ReqIF-WF.Type: Requirement

###### KMSA-FDII-CCIH-IGBE_test: Test
For application software development and alarm lines testing, it is possible to trigger an alarm using PMURx_UR_NVMCON3.ECCERRINJ without impact on the mission logic.
- ReqIF-WF.Type: Requirement

###### KMSA-FDII-CCIH-IGBE_reporting: Reporting
Upon detection of a fault in the ECC correction logic an alarm is generated.
- ReqIF-WF.Type: Information

###### KMSA-FDII-CCIH-IGBE_recommendederrorreaction: Recommended error reaction
If the alarm is due to a PRRAM ECC online monitor error, it is recommended to do a application reset.
In case of a transient error, the fault would be removed.
A permanent error would show up again early when using LBIST or with first reads from the PRRAM bank. In that case, the system integrator shall evaluate the most appropriate reaction.
For ASIL functions using the RRAM, system integrator shall consider the PRRAM bank as non-operational and take appropriate reaction. If the alarm is due to an uncorrectable error, the reaction depends on the ASIL requirements allocated to the function using the RRAM:
- For QM functions using the RRAM, system Integrator shall evaluate the most appropriate reaction
- For ASIL functions using the RRAM, system Integrator shall consider the RRAM Bank as non-operational and take appropriate reaction
- ReqIF-WF.Type: Information

###### AFPA-FDII-CIFG-FFJB: SM[HW]:NVMR:PNVM_WAIT_STATE_PROTECTION
- IFX.Version: 5
- ReqIF-WF.Type: Heading

###### AFPA-FDII-CIFG-FFJB_description: Description
The safety mechanism checks for unintentional changes in the wait state configuration of the PMUR to protect the PRRAM read timings. The wait state configuration is protected using an Error Correction Code (ECC) mechanism with single bit error and double bit error detection capabilities.
- ReqIF-WF.Type: Information

###### AFPA-FDII-CIFG-FFJB_resetoperationalstate: Reset operational state
This safety mechanism is active after application reset.
- ReqIF-WF.Type: Information

###### AFPA-FDII-CIFG-FFJB_configurationandactivation: Configuration and activation
N.A.
- ReqIF-WF.Type: Requirement

###### AFPA-FDII-CIFG-FFJB_test: Test
For application software development and alarm lines testing, it is possible to trigger an alarm using PMUR_UR_NVMCON3. WSERRINJ without impact on the mission logic.
- ReqIF-WF.Type: Requirement

###### AFPA-FDII-CIFG-FFJB_reporting: Reporting
Upon detection of a fault in the wait state configuration observed by ECC, an alarm is generated by the counter part SM[HW]:CPU:CFI_WAIT_STATE_PROTECTION.
Please refer to the alarm table for the CPU alarms to get the alarm number to be used.
- ReqIF-WF.Type: Information

###### AFPA-FDII-CIFG-FFJB_recommendederrorreaction: Recommended error reaction
A safety alarm might indicate a register bit flip. It is recommended to perform a write of the wait state configuration to the PRRAM wait state register for either HOST or for CSRM (depending on the alarm). As an alternative an application reset can be done to initialize the register with the application reset value.
- ReqIF-WF.Type: Information

###### VMWA-FDII-DBBG-GHGJ: SM[HW]:NVMR:REG_MONITOR
- IFX.Version: 10
- ReqIF-WF.Type: Heading

###### VMWA-FDII-DBBG-GHGJ_description: Description
This safety mechanism also commonly called safety flip-flop (SFF) detects and corrects transient and permanent faults in configuration registers and internal safety relevant states of the RRAM by using Triple Modular Redundancy (TMR) Safety Flip-flops (SFF).
The safety mechanism is used for the following register bits:
- Read settings and control flip-flops in the PMUR:
- PMUR_UR_NVMCON2.ECCCORDIS
- PMUR_UR_NVMCON2.MASKUECC
- Error management settings in the PMUR:
- PMUR_UR_NVMCON2.RECDIS
- PMUR_UR_NVMCON2.ECCSCLR
- PMUR_UR_NVMCON2.SEABCLR
- PMUR_UR_NVMCON2.DEABCLR
- PMUR_UR_NVMCON2.BFABCLR
- PMUR_UR_NVMCON2.UBABCLR
- Error management valid bits in the PMUR:
- UR_DEABx.VLD
- UR_BFABx.VLD
- UR_UBAB0.VLD
- ReqIF-WF.Type: Information

###### VMWA-FDII-DBBG-GHGJ_resetoperationalstate: Reset operational state
This safety mechanism is reset according to the reset behavior of each of the registers above, as specified in the register overview - PMUR table in the user manual.
- ReqIF-WF.Type: Information

###### VMWA-FDII-DBBG-GHGJ_configurationandactivation: Configuration and activation
N.A.
- ReqIF-WF.Type: Requirement

###### VMWA-FDII-DBBG-GHGJ_test: Test
The following software routine shall be used to run the self-test :
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### VMWA-FDII-DBBG-GHGJ_reporting: Reporting
Upon detection of a fault an alarm to the SMU is generated. This alarm is triggered in the event of a correctable one bit error or an uncorrectable two bit error.
- ReqIF-WF.Type: Information

###### VMWA-FDII-DBBG-GHGJ_recommendederrorreaction: Recommended error reaction
System integrator to select an appropriate safe reaction in the SMU.
If the system integrator wishes to avoid an immediate reset of the MCU, the following actions can be attempted:
- Rewrite RRAM configurations in the PMUR_UR_NVMCON2 registers
- If alarm persists: clear the error address buffer registers DEAB, BFAB, UBAB
If after these two actions the alarm still persists, then an application reset is recommended.
- ReqIF-WF.Type: Information

###### FXPA-FDII-DEBJ-AEGD: SM[HW]:NVMR:STARTUP_PROTECTION
- IFX.Version: 1
- ReqIF-WF.Type: Heading

###### FXPA-FDII-DEBJ-AEGD_description: Description
This safety mechanism detects unauthorized access to resources that are only accessible while MCU boot. This ensures freedom from interference from QM masters with potential systematic faults as well as transient and permanent faults occurring while SRI transactions and guarantees that configuration installed as MCU boot remains untouched. After MCU start-up, it is not possible for the application software to change start-up protected registers.
This special access protection is realized as a cooperation between the Start-up Software (SSW) and the hardware. The SSW is part of the System Firmware (FW) stored in the Boot ROM. The SSW is the program and data code executed after every MCU start-up in user mode to configure the device and trigger the user code execution. The start-up protection enables and disables write accesses to resources in different Functional Blocks that determine the MCU system characteristics and configurations. The start-up protection bit SMM_STCON.ST_PROT is used to configure the MCU start-up protection.
If the MCU start-up protection is disabled (SMM_STCON.ST_PROT = 0 B), the SSW may write to the start-up protected registers to define the MCU system characteristics. On completion of start-up, the SSW enables start-up protection (SMM_STCON.ST_PROT = 1 B) to prevent the Application SW from updating the start-up protected registers.
All registers or bit-fields showing the STP protection and the ICB are protected by this safety mechanism.
- ReqIF-WF.Type: Information

###### FXPA-FDII-DEBJ-AEGD_resetoperationalstate: Reset operational state
This safety mechanism is active after application reset.
- ReqIF-WF.Type: Information

###### FXPA-FDII-DEBJ-AEGD_configurationandactivation: Configuration and activation
The safety mechanism is active once the start-up protection register is set by the SSW.
- ReqIF-WF.Type: Requirement

###### FXPA-FDII-DEBJ-AEGD_test: Test
The mechanism can be tested by executing an access on an STP protected register.
- ReqIF-WF.Type: Requirement

###### FXPA-FDII-DEBJ-AEGD_reporting: Reporting
On detection of an access protection violation the NVMR signals a SRI Bus Error Event, which is detected by the SRI BCU that signals an alarm.
- ReqIF-WF.Type: Information

###### FXPA-FDII-DEBJ-AEGD_recommendederrorreaction: Recommended error reaction
System integrator to select an appropriate safe reaction in the SMU.
- ReqIF-WF.Type: Information

###### OAIA-FEJI-GDIC-GEEA: SM[HW]:NVMR:CFG_AS_AP
- IFX.Version: 1
- ReqIF-WF.Type: Heading

###### OAIA-FEJI-GDIC-GEEA_description: Description
The NVMR behaves as a slave on the SRI bus. The NVMR receives read and write requests and will detect by this safety mechanism if the master requesting the transaction is enabled for the type of access.
This ensures freedom from interference from QM masters with potential systematic faults as well as transient and permanent faults occurring while SRI transactions.
This is realized following the PROT-APU access protection scheme checking via unique TAG-IDs that a master is enabled to read or write a slave. For the NVMR different ACCEN access protection registers are implemented to authorize:
1. The read and write access to the HOST and CSRM request registers: PROT_ACCENREQ**
Unauthorized read or write accesses to the NVMR request registers lead to a SRI bus error and an SRI XBAR Bus Error Event Alarm (or SRI XBAR SM Bus Error Event Alarm for special master accesses) is raised by the XBAR. The requested read or write operation to a register is not executed
2. The read access to the HOST and CSRM DNVM & UCB:PROT_ACCENDR**, PROT_ACCENUCB**Unauthorized read accesses to the HOST and CSRM DNVM & UCB lead to a SRI bus error and an SRI XBAR Bus Error Event Alarm (or SRI XBAR SM Bus Error Event Alarm for special master accesses) is raised by the XBAR. The requested read operation is not executed
For a complete list of the registers protected by PROT, see tables ‘Register overview – access mode glossary’ and ‘Register overview – PMUR (ascending off set address)’ and ‘Register overview – DMUR (ascending off set address)’ in the user manual.
- ReqIF-WF.Type: Information

###### OAIA-FEJI-GDIC-GEEA_resetoperationalstate: Reset operational state
An application reset will set the configuration of this safety mechanism back to its default value.
- ReqIF-WF.Type: Information

###### OAIA-FEJI-GDIC-GEEA_configurationandactivation: Configuration and activation
This safety mechanism is active after intentional configuration by application software through the ACCEN registers.
- ReqIF-WF.Type: Requirement

###### OAIA-FEJI-GDIC-GEEA_test: Test
The mechanism can be tested by an access which is in violation of the current ACCEN configuration.
- ReqIF-WF.Type: Requirement

###### OAIA-FEJI-GDIC-GEEA_reporting: Reporting
Upon the detection of an access violation, a SRI Bus Error Event together with the alarm is generated.
- ReqIF-WF.Type: Information

###### OAIA-FEJI-GDIC-GEEA_recommendederrorreaction: Recommended error reaction
Beside the actual safety alarm there is an automatic blocking of the command execution. System integrator shall evaluate the most appropriate reaction.
- ReqIF-WF.Type: Information

###### KINA-FEJI-GEHC-GABF: SM[HW]:NVMR:SV_AP
- IFX.Version: 1
- ReqIF-WF.Type: Heading

###### KINA-FEJI-GEHC-GABF_description: Description
Critical module registers are implemented with a write access restriction that allows access only to masters with supervisor (SV) mode privilege. Unauthorized access attempts are blocked by this mechanism.
For a list of the registers protected by SV, see tables ‘Register Overview – Access Mode Glossary’ and ‘Register Overview – DMUR (ascending offset address)’ and ‘Register Overview – PMUR (ascending offset address)’ in the User Manual.
- ReqIF-WF.Type: Information

###### KINA-FEJI-GEHC-GABF_resetoperationalstate: Reset operational state
The safety mechanism is active after application reset.
- ReqIF-WF.Type: Information

###### KINA-FEJI-GEHC-GABF_configurationandactivation: Configuration and activation
N.A.
- ReqIF-WF.Type: Requirement

###### KINA-FEJI-GEHC-GABF_test: Test
This safety measure can be tested by a write access to a protected register by a master agent function without Supervisor (SV) access rights.
- ReqIF-WF.Type: Requirement

###### KINA-FEJI-GEHC-GABF_reporting: Reporting
For DMUR, on detection of an unauthorized access to the ACCEN registers or to the PROT mechanism itself an SRI bus alarm is generated.
For PMUR, the event signal is called sx_cpupfrwbsfr_sfr_err_o, which is sent to CPU. Please refer to the ‘Program flash interface (CPU-PFI)’ chapter in User Manual for further information.
- ReqIF-WF.Type: Information

###### KINA-FEJI-GEHC-GABF_recommendederrorreaction: Recommended error reaction
System integrator to select appropriate safe reaction in SMU.
- ReqIF-WF.Type: Information

###### YEEA-FEJI-GFCH-CJJE: SM[HW]:NVMR:SAFETY_ENDINIT
- IFX.Version: 4
- ReqIF-WF.Type: Heading

###### YEEA-FEJI-GFCH-CJJE_description: Description
The RRAM provides a unique PROT mechanism that protects the configuration of the access protection mechanism (ACCEN). The ACCEN mechanism is based on the master agent function identifier. This supports freedom from interference of different software tasks. Unauthorized access attempts are blocked by this mechanism. Several protection groups are defined in the RRAM as listed below.
Each PROT** mentioned in the table protects the ACCEN** registers mentioned in the "related ACCEN" column. In addition it is mentioned which resource is protected by the ACCEN registers.
Protection
scheme
| PROT | Related ACCEN | Related resource |
| --- | --- | --- |
| PROT_PROTPR | N.A. | P-RRAM memory |
| PROT_PROTDR | PROT_ACCENDR**, PROT_ACCENUCB** | D-RRAM (EEPROM) and UCB memory |
| PROT_PROTREQ | PROT_ACCENREQ** | Request register interface |
| PROT_PROTTR | N.A. | Test registers (valid for PMUR and DMUR) |
For a complete list of the registers protected by PROT, see tables ‘Register overview – access mode glossary’ and ‘Register overview – PMUR (ascending off set address)’ and ‘Register overview – DMUR (ascending off set address)’ in the user manual.
- ReqIF-WF.Type: Information

###### YEEA-FEJI-GFCH-CJJE_resetoperationalstate: Reset operational state
An application reset will set the configuration of this safety mechanism back to its default value.
For the HOST memories the reset state of the PROT is initialized without an owner defined (ODEF = 0 B). For the CSRM memories the reset state of the PROT is initialized with owner defined (ODEF = 1 B, owner: CPUCS, see reset value of register description).
Note: The reset values for PROT/APU ensure that only CPUCS can access the relevant registers within the shared bank PMUR1 and within DMURCS.
- ReqIF-WF.Type: Information

###### YEEA-FEJI-GFCH-CJJE_configurationandactivation: Configuration and activation
The safety mechanism is active after intentional configuration by the application software through the PROT** registers of the table above.
- ReqIF-WF.Type: Requirement

###### YEEA-FEJI-GFCH-CJJE_test: Test
This safety measure can be tested after the PROT owner has been configured:
Write access to a protected register by a master agent function that is not the PROT owner
- ReqIF-WF.Type: Requirement

###### YEEA-FEJI-GFCH-CJJE_reporting: Reporting
For DMUR, on detection of an unauthorized access to the ACCEN registers or to the PROT mechanism itself an SRI bus alarm is generated.
For PMUR, the event signal is called sx_cpupfrwbsfr_sfr_err_o, which is sent to CPU. Please refer to the ‘Program flash interface (CPU-PFI)’ chapter in User Manual for further information.
- ReqIF-WF.Type: Information

###### YEEA-FEJI-GFCH-CJJE_recommendederrorreaction: Recommended error reaction
System integrator to select an appropriate safe reaction in the SMU.
- ReqIF-WF.Type: Information

###### JMXA-FEAA-DCCE-HADF: SM[HW]:NVMR:PNVM_ERROR_MANAGEMENT
- IFX.Version: 8
- ReqIF-WF.Type: Heading

###### JMXA-FEAA-DCCE-HADF_description: Description
The PRRAM ECC error management safety mechanism also commonly called error address buffer will:
- Monitor single located ECC byte errors (single erasure) in the read data of the PRRAM. The application SW shall monitor the frequency of these events
- Monitor double located ECC byte errors (double erasure) in the read data of the PRRAM and send an alarm when technology dependent threshold is reached
- Monitor the unlocated ECC byte errors (bit-flip) in the read data of the PRRAM and send an alarm when technology dependent threshold is reached
- Monitor the uncorrectable byte errors in the read data of the PRRAM and send an alarm
For each detected error, the address is stored uniquely in the corresponding address buffer register. A full set of address buffer registers leads to an SMU alarm.
The threshold is defined with the following configuration:
- PMURx_UR_SEABx: Single Erasure Address Buffer stores 7 addresses. No alarm is sent when the buffer is full
- PMURx_UR_DEAB0 : Double Erasure Address Buffer stores 1 address and sends an alarm on the 1st error found
- PMURx_UR_BFABx: Bit-flip Address Buffer stores 2 addresses and sends an alarm on the 2nd error found as long as the SEAB is not full. If the SEAB is full an BFAB alarm is on the first entry.
- PMURx_UR_UBAB0: Uncorrectable Byte error Address Buffer stores only 1 address and sends an alarm on the 1st error found
Please refer to the description of the PMURx_UR_SEABx (x = 0-6), PMURx_UR_DEAB0, PMURx_UR_BFABx (x = 0-1) and PMURx_UR_UBAB0 for more details about the register access and content.
- ReqIF-WF.Type: Information

###### JMXA-FEAA-DCCE-HADF_resetoperationalstate: Reset operational state
This safety mechanism is active after application reset.
- ReqIF-WF.Type: Information

###### JMXA-FEAA-DCCE-HADF_configurationandactivation: Configuration and activation
The safety mechanism is theoretically active directly after application reset but can only be used once a read on the PRRAM is possible, meaning once the MCU boot process has installed the necessary read conditions.
The prerequisites for the good functioning of this safety mechanism are:
- The software shall enable the xAB recording using PMURx_UR_NVMCON2.RECDIS = 0B (default reset value)
- The software can initialize the xAB by clearing using PMURx_UR_NVMCON2.SEABCLR, PMURx_UR_NVMCON2.DEABCLR, PMURx_UR_NVMCON2.BFABCLR and PMURx_UR_NVMCON2.UBABCLR
The default value of PMURx_UR_NVMCON2.RECDIS makes the safety mechanism already operational after reset.
- ReqIF-WF.Type: Requirement

###### JMXA-FEAA-DCCE-HADF_test: Test
For application software development and alarm lines testing, it is possible to trigger an alarm using PMURx_UR_NVMCON3.DEABERRINJ, PMURx_UR_NVMCON3.BFABERRINJ and PMURx_UR_NVMCON3.UBABERRINJ without impact on the mission logic (no entry is written in the xABs).
- ReqIF-WF.Type: Requirement

###### JMXA-FEAA-DCCE-HADF_reporting: Reporting
Upon detection of the address buffers being full, the respective alarms are generated.
- ReqIF-WF.Type: Information

###### JMXA-FEAA-DCCE-HADF_recommendederrorreaction: Recommended error reaction
In case of SEAB overflow system Integrator shall evaluate the most appropriate reaction (for example no alarm reaction). For safety related code in the PRRAM the SEAB buffer shall be monitored and if there is an overflow this should be taken as early warning. This means the PRRAM is still available but it is nearing the critical error range.
In case of DEAB or BFAB overflow alarm reaction depends on the ASIL requirements allocated to the function using the RRAM:
- For QM functions using the PRRAM, system Integrator shall evaluate the most appropriate reaction (for example no alarm reaction)
- For ASIL functions using the PRRAM, on occurrence of the first alarm of DEAB or BFAB the fault is still correctable but it is recommended to rewrite all the faulty addresses.
Rationale: In case of DEAB or BFAB overflow the probability of uncorrectable errors are in the same range as a further bit-flip error.
In case of UBAB overflow alarm reaction depends on the ASIL requirements allocated to the function using the PRRAM:
- For QM functions using the PRRAM, system Integrator shall evaluate the most appropriate reaction
- For ASIL functions using the PRRAM, system Integrator shall consider the PRRAM Bank as non-operational and take appropriate reaction
- ReqIF-WF.Type: Information

##### NNEA-FEJI-GBGF-HAEF: Alarms
NVMR alarms – PMUR
| Alarm name | Safety mechanism | Alarm flag to be cleared in |
| --- | --- | --- |
| PMUR ECC erasure address buffer (DEAB) full | SM[HW]:NVMR:PNVM_ERROR_MANAGEMENT | SMU and PMUR through executing a new PNVM read (on a non-errored address) and using PMURx_UR_NVMCON2.DEABCLR |
| PMUR ECC bitflip address buffer (BFAB) full | SM[HW]:NVMR:PNVM_ERROR_MANAGEMENT | SMU and PMUR through executing a new PNVM read (on a non-errored address) and using PMURx_UR_NVMCON2.BFABCLR |
| PMUR ECC uncorrectable error address buffer (UBAB) full | SM[HW]:NVMR:PNVM_ERROR_MANAGEMENT | SMU and PMUR through executing a new PNVM read (on a non-errored address) and using PMURx_UR_NVMCON2.UBABCLR |
| PMUR static configurations MISR error | SM[HW]:NVMR:MISR | - SMU - Application reset |
| PMUR ECC error | SM[HW]:NVMR:PNVM_ECC_ONLINE_MONITOR | SMU and PMUR through executing a new PNVM read (on a non-errored address) and using PMURx_UR_NVMCON2.ECCSCLR |
| PMUR dynamic configurations SFF error | SM[HW]:NVMR:REG_MONITOR | SMU only |
| SRI Bus Error Event | SM[HW]:NVMR:STARTUP_PROTECTION SM[HW]:NVMR:SV_AP SM[HW]:NVMR:CFG_AS_AP SM[HW]:NVMR:SAFETY_ENDINIT | SMU only |
NVMR alarms – DMUR
| Alarm name | Safety mechanism | Alarm flag to be cleared in |
| --- | --- | --- |
| DMUR static configurations MISR error | SM[HW]:NVMR:MISR | - SMU - Application reset |
| NVMR SRI Address Phase EDC Error | SM[HW]:SRI:SRI_TRANSACTION_INTEGRITY | SMU only |
| NVMR SRI Write Data Phase EDC Error | SM[HW]:SRI:SRI_TRANSACTION_INTEGRITY | SMU only |
| SRI Bus Error Event | SM[HW]:NVMR:STARTUP_PROTECTION SM[HW]:NVMR:SV_AP SM[HW]:NVMR:CFG_AS_AP SM[HW]:NVMR:SAFETY_ENDINIT | SMU only |
NVMR alarms –
BootROM
| Alarm name | Safety mechanism | Alarm flag to be cleared in |
| --- | --- | --- |
| NVMR SRI Address Phase EDC Error | SM[HW]:NVMR:BOOTROM_ADDR_PROTECTION | SMU only |
| NVMR SRI Write Data Phase EDC Error | SM[HW]:NVM:BOOTROM_ERROR_CORRECTION | SMU only |
- IFX.Version: 1
- ReqIF-WF.Type: Information

##### OAGA-FEJI-EIJF-IJIB: External safety mechanisms
- IFX.Version: 1
- ReqIF-WF.Type: Information

###### ZDDA-FDII-BICF-GIFF: ESM[SW]:NVMR:CONFIG_READBACK
- IFX.Version: 1
- ReqIF-WF.Type: Heading

###### ZDDA-FDII-BICF-GIFF_description: Description
The software shall detect faults in the NVM configurations by reading back the configured registers and checking against the expected values.
A mismatch might be due to transient or permanent register faults or due to a software failure during the writing of the registers. It is recommended to write the registers again and repeat the check; if the error persists, it is recommended to do a system reset.
The following registers have to be read back after writing to ensure a safe read on the HOST bank PMUR0:
- PMUR0_UR_PRWAIT
- PMUR0_UR_NVMCON2
A check of the configuration registers of the shared bank PMUR1 after writing shall be done from the following configured registers:
- PMUR1_UR_PRWAIT
- PMUR1_UR_NVMCON2
Note: The shared bank is shared between HOST and CSRM applications.
- ReqIF-WF.Type: Requirement

###### NZKA-FDII-BIDD-CABA: ESM[SW]:NVMR:UCB_READBACK
- IFX.Version: 1
- ReqIF-WF.Type: Heading

###### NZKA-FDII-BIDD-CABA_description: Description
After programming a new value in a UCB, the [application SW] shall detect a fault in the UCB or a failure of the UCB writing process by reading back the configured UCB and checking against the expected value.
Upon detection of a mismatch, the [application SW] shall rewrite the UCB if possible and repeat the ESM. If the error persists or a rewrite is not possible then the content of this UCB shall not be used during the next MCU start-up.
For dual UCBs with ORIG and COPY versions, the ORIG is evaluated first; if the fault happened during the update of the UCB COPY and the content of the UCB ORIG is still readable as configured then a start-up after the next reset is still possible.
If the fault happened during the update of the UCB ORIG then it must be ensured that the content of the UCB COPY is still readable with the configured content. If the content of the UCB COPY is still readable with the configured content then the update of the UCB ORIG can be repeated.
In addition, it is recommended to trigger an alarm and decide on further appropriate reaction.
- ReqIF-WF.Type: Requirement

###### HFDA-FEAA-DJDH-FHHH: ESM[SW]:NVMR:PNVM_INTEGRITY_CHECK
- IFX.Version: 1
- ReqIF-WF.Type: Heading

###### HFDA-FEAA-DJDH-FHHH_description: Description
Within Latent Fault Diagnostic Time Interval, the application software shall compare the PNVM checksum of all safety related code with an expected PNVM checksum. If the calculated and expected PNVM checksums do not match, the application software shall trigger an alarm.
Note:
This ESM aims to reduce the latent fault metric (LFM) of PNVM. Since ECC can only detect errors during read accesses, all non-read location can potentially accumulate errors (latent faults). Without using this integrity check, undetected latent faults can accumulate into uncorrectable errors.
Recommendations: the PNVM checksum could be calculated using [DMA] to read PNVM and Flexible CRC Engine [FCE] to calculate CRC. This would reduce CPU load. Expected PNVM checksum could be reused from a value stored by the ESM[SW]:NVMR:PFLASH_UPDATE_CHECK. A low priority background scan during one driving cycle could be sufficient.
In order to locate the errors present in the PNVM at start-up, IFX recommends to read the entire PNVM and incidentally compute a CRC over the data. The user will be notified by an [SMU] alarm if the SM[HW]:NVMR:PNVM_ERROR_MANAGEMENENT (that is error buffers) has detected an overflow of buffer entries, which indicates an unexpected high rate of latent (erasure/bit-flip) faults; in addition an uncorrectable fault would also be detected.
Note: This external safety mechanism recommends the usage of SM[HW]:NVMR:PNVM_ERROR_MANAGEMENT. The configurations and activation conditions from this safety mechanism are to be followed. The values of the ERAB/BFAB and UBAB registers show the number of erasure, bit-flip and uncorrectable errors for the Bank(s) under investigation.
Note: By checking of inactive PNVM Banks the reaction on ERAB/BFAB/UBAB alarms (of SM[HW]:NVMR:PNVM_ERROR_MANAGEMENT) might be for monitoring only because there is no code execution from these sectors.
On detection of CRC mismatch or an error buffer overflow of the ERAB/BFAB and UBAB registers, the content of the PNVM cannot be trusted anymore. Safety alarms allow to detect which PNVM Bank is affected. The application software shall trigger an alarm and decide on an appropriate reaction.
- ReqIF-WF.Type: Requirement

###### APLA-FEAA-DACJ-DEBA: ESM[SW]:NVMR:PNVM_UPDATE_CHECK
- IFX.Version: 5
- ReqIF-WF.Type: Heading

###### APLA-FEAA-DACJ-DEBA_description: Description
After update of PRRAM content and before starting safety related application software, the application software shall compare the PRRAM checksum of all safety related code with an expected PRRAM checksum. If the calculated and expected PRRAM checksums do not match, the application software shall trigger an alarm.
Note: This ESM aims to reduce the latent fault metric (LFM) of PRRAM. Since ECC can only detect errors during read accesses, all non-read location can potentially accumulate errors (latent faults). Without using this update check, undetected latent faults can accumulate into uncorrectable errors.
Recommendations: the PRRAM checksum could be calculated using [DMA] to read PRRAM and Flexible CRC Engine [FCE] to calculate CRC. This would reduce CPU load. After validation of written data the expected checksum should be stored in the PRRAM for further use by the ESM[SW]:NVMR:PNVM_INTEGRITY_CHECK.
In order to locate the errors present in the PRRAM after content update, IFX recommends to read the entire PRRAM and compute a CRC over the data. The user will be notified by an SMU alarm if the SM[HW]:NVMR:PNVM_ERROR_MANAGEMENT (i.e. error buffers) has detected an overflow of buffer entries, which indicates an unexpected high rate of latent (erasure/bit-flip) faults; in addition an uncorrectable fault would also be detected.
Note: This external safety mechanism recommends the usage of SM[HW]:NVMR:PNVM_ERROR_MANAGEMENT. The configurations and activation conditions from this safety mechanism are to be followed. The values of the ERAB/BFAB and UBAB registers show the number of erasure, bit-flip and uncorrectable errors for the Bank(s) under investigation.
On detection of CRC mismatch or an error buffer overflow of the DEAB/BFAB and UBAB registers, the content of the PRRAM cannot be trusted anymore. Safety alarms allow to detect which PRRAM bank is affected.
The operating conditions (for example supply voltages) shall be checked and monitored. If the fault occurred in the written PRRAM region the update of that region shall be done again (meaning reprogramming of the content). Then the ESM[SW]:NVMR:PNVM_UPDATE_CHECK shall be done again. If up to two repetitions at correct operating conditions lead again to errors then the PRRAM region cannot be used anymore and the application software shall trigger an alarm and decide on an appropriate reaction.
- ReqIF-WF.Type: Requirement

###### HLBA-FEAA-DAEE-JBGC: ESM[SW]:NVMR:EEPROM_DRIVER_D
- IFX.Version: 5
- ReqIF-WF.Type: Heading

###### HLBA-FEAA-DAEE-JBGC_description: Description
After read of safety related RRAM.EEPROM content and before using the data in safety related function, the application software shall validate the RRAM.EEPROM data consistency with an expected RRAM.EEPROM information redundancy (for example stored in RRAM.EEPROM). The expected information redundancy shall also cover the target address of the data storage. If the calculated and expected RRAM.EEPROM information redundancy do not match, the application software shall trigger an alarm.
Note: This external safety mechanism aims to reduce the single point fault metric (SPFM) and latent fault metric (LFM) of RRAM.EEPROM.
The operating conditions (for example supply voltages) shall be checked and monitored.
It is recommended to validate the data consistency also directly after the write operation. If the fault occurred in the written RRAM.EEPROM region, the update of that region shall be done again by using one or several of the following RRAM operations:
1. Rewrite data
2. Repair of failing RRAM region and rewrite the data again
3. Write data in a different RRAM memory region
Rewrite data may consist of a repetition of write commands with the same data or a sequence of erase and rewrite if applicable/available.
Repair means the use of the Online Wordline remap request.
Then the validation of the RRAM.EEPROM data consistency shall be done again. If the RRAM operations at correct operating conditions lead again to errors then the RRAM region cannot be used anymore and the application software shall trigger an alarm and decide on an appropriate reaction.
- ReqIF-WF.Type: Requirement

###### ACTA-FEAA-DCJJ-HIJI: ESM[SW]:NVMR:EEPROM_DRIVER_B
- IFX.Version: 5
- ReqIF-WF.Type: Heading

###### ACTA-FEAA-DCJJ-HIJI_description: Description
After read of safety related RRAM.EEPROM content and before using the data in safety related function, the application software shall validate the RRAM.EEPROM data consistency with an expected RRAM.EEPROM information redundancy (for example stored in RRAM.EEPROM). The expected information redundancy shall also cover the target address of the data storage. If the calculated and expected RRAM.EEPROM information redundancy do not match, the application software shall trigger an alarm.
Note: This external safety mechanism aims to reduce the single point fault metric (SPFM) and latent fault metric (LFM) of RRAM.EEPROM.
Note: For this external safety mechanism the use of Infineon MCAL FLS and FEE drivers is recommended.
The operating conditions (for example supply voltages) shall be checked and monitored.
It is recommended to validate the data consistency also directly after the write operation. If the fault occurred in the written RRAM.EEPROM region, the update of that region shall be done again by using one or several of the following RRAM Operations:
1. Rewrite data
2. Repair of failing RRAM region and rewrite the data again
3. Write data in a different RRAM memory region
Rewrite data may consist of a repetition of write commands with the same data or a sequence of erase and rewrite if applicable/available.
Repair means the use of the Online Wordline remap request.
Then the validation of the RRAM.EEPROM data consistency shall be done again. If the RRAM operations at correct operating conditions lead again to errors then the RRAM region cannot be used anymore and the application software shall trigger an alarm and decide on an appropriate reaction.
- ReqIF-WF.Type: Requirement

#### PYAA-EDCJ-DDAH-BHFE: Power Management System (PMS)
The Power Management System (PMS) provides supply voltage selection, internal supply voltage generation, supply voltage monitoring, power domain and isolation control, and power management functions for the microcontroller. It also supports other microcontroller infrastructure functions through reset triggers, standby mode transitions, and real-time clock services.
- IFX.Version: 1
- ReqIF-WF.Type: Information

##### ISUA-FAFF-HDCJ-EGCF: Internal safety mechanisms
- IFX.Version: 1
- ReqIF-WF.Type: Information

###### MPUA-EHGE-CGGJ-JJBG: SM[HW]:PMS:REG_MONITOR
- IFX.Version: 1
- ReqIF-WF.Type: Heading

###### MPUA-EHGE-CGGJ-JJBG_description: Description
The PMS implements safety flip-flops for detecting transient or permanent faults in the configuration registers and sequential logic. Safety flip-flops are special flip-flops that implement a hardware mechanism capable to detect bit-flip within the flip-flops. The configuration and control registers which are designed with safety flip-flops are listed below:
- VMONP_VDDCON
- VMONP_VDDRST
- VMONP_VDDCLDRST
- VMONP_VDDEXTCON
- VMONP_VDDEXTRST
- VMONP_VSSDCHSCON
- VMONP_VSSDCHSRST
- VMONP_VDDEXTDCCON
- VMONP_VDDEXTDCRST
- VMONP_VDDDCLSCON
- VMONP_VDDDCLSRST
- VMONP_VDDEVRSBCON
- VMONP_VDDEVRSBRST
- VMONP_VDDMCON
- VMONP_VDDMRST
- VMONP_VDDPHPHY0CON
- VMONP_VDDPHPHY0RST
- VMONP_VDDPHPHY1RST
- VMONP_VDDPHPHY1CON
- VMONP_VDDHSIFCON
- VMONP_VDDHSIFRST
- VMONP_VDDSBCON
- VMONP_VDDSBRST
- VMONP_VDDCPUACON
- VMONP_VDDCPUARST
- VMONP_VDDCPUBCON
- VMONP_VDDCPUBRST
- VMONP_VDDPPUCON
- VMONP_VDDPPURST
- VMONP_VDDPHY0CON
- VMONP_VDDPHY0RST
- VMONP_VDDPHY1CON
- VMONP_VDDPHY1RST
- VMONP_VDDPHRIF0CON
- VMONP_VDDPHRIF0RST
- VMONP_VDDPHPHY2CON
- VMONP_VDDPHPHY2RST
- VMONP_VDDPHRIF1CON
- VMONP_VDDPHRIF1RST
- VMONP_VDDP3NVMCON
- VMONP_VDDP3NVMRST
- VMONP_VDDPADCON
- VMONP_VDDPADRST
- VMONP_VDDLMU0CON
- VMONP_VDDLMU0RST
- VMONP_VDDLMU1CON
- VMONP_VDDLMU1RST
- VMONP_VDDPCIE1CON
- VMONP_VDDPCIE1RST
- VMONP_VDDRIF0CON
- VMONP_VDDRIF0RST
- VMONP_VDDRIF1CON
- VMONP_VDDRIF1RST
- VMONS_VDDEVRSBCON
- VMONS_VDDEXTCON
- VMONS_VDDMCON
- VMONS_VDDFLEXCON
- VMONS_VDDCON
- VMONS_VDDPMS0CON
- VMONS_VDDPMS1CON
- VMONS_VDDPMS2CON
- VMONS_VDDPHPHY0CON
- VMONS_VDDPHPHY1CON
- VMONS_VDDHSIFCON
- VMONS_VDDPHY0CON
- VMONS_VDDPHY1CON
- VMONS_VDDSBCON
- VMONS_VDDCPUACON
- VMONS_VDDCPUBCON
- VMONS_VDDPPUCON
- VMONS_VDDEXTDCCON
- VMONS_LVLSEL
- VMONS_VDDPADCON
- VMONS_VDDPHRIF0CON
- VMONS_VDDPHPHY2CON
- VMONS_VDDPHRIF1CON
- VMONS_VDDP3NVMCON
- VMONS_VDDRIF0CON
- VMONS_VDDLMU0CON
- VMONS_VDDLMU1CON
- VMONS_VDDPCIE1CON
- VMONS_VDDRIF0CON
- VMONS_VDDRIF1CON
- VID_CON0
- VID_CON1
- PD_CON0
- PD_CON1
- PAD_CON
- PAD_ESR2CON
- HPOSCCON1
- WAKEUP_CON0
- WAKEUP_CON1
- STANDBY_CON0
- WUT_CON
- SCR_CON0
- EVRC_CON0
- EVRC_CON1
- EVRC_CON2
- EVRC_CON3
- EVRC_CON4
- EVRC_COEFF0
- EVRC_COEFF1
- EVRC_COEFF2
- EVRC_COEFF3
- EVRC_COEFF4
- EVRC_COEFF5
- RTC_CON0
- RTC_CON1
- RTC_CON2
- RTC_CMP0
- RTC_CMP1
- DTS_CON
- DTS_LIM1
- DTS_LIM2
Note: Not all registers are available in all derivatives
- ReqIF-WF.Type: Information

###### MPUA-EHGE-CGGJ-JJBG_resetoperationalstate: Reset operational state
This safety mechanism is reset according to the reset behavior of each of the registers above, as specified in the Register Overview - PMS table in the User Manual.
- ReqIF-WF.Type: Information

###### MPUA-EHGE-CGGJ-JJBG_configurationandactivation: Configuration and activation
N.A.
- ReqIF-WF.Type: Requirement

###### MPUA-EHGE-CGGJ-JJBG_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### MPUA-EHGE-CGGJ-JJBG_reporting: Reporting
Upon detection of a fault, a PMS SFF Uncorrectable Error Alarm will be reported to the SMU.
- ReqIF-WF.Type: Information

###### MPUA-EHGE-CGGJ-JJBG_recommendederrorreaction: Recommended error reaction
System integrator to select appropriate safe reaction in SMU.
- ReqIF-WF.Type: Information

###### RHHA-EHGE-EGEJ-EEHE: SM[HW]:PMS:STBY_CTRL
- IFX.Version: 1
- ReqIF-WF.Type: Heading

###### RHHA-EHGE-EGEJ-EEHE_description: Description
The entry into stand-by mode is only possible if two control signals are active at the same time. One signal is triggered by SMM through setting of PMCSRn.REQSLP (n=0..5) (in SMM) or assertion of ESRx (x=1..2) and the other is set through PMSWCR1.PROCMODEEN or STANDBY_CON1.SWESRSBEN or STANDBY_CON0.ESR2SBEN. Therefore an unintended standby entry is avoided.
Standby entry gating
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- ReqIF-WF.Type: Information

###### RHHA-EHGE-EGEJ-EEHE_resetoperationalstate: Reset operational state
Dependent on the reset behavior of the respective register. Please see the tables Registers Overview - PMS and Registers Overview - SMM in the User Manual Information.
- ReqIF-WF.Type: Information

###### RHHA-EHGE-EGEJ-EEHE_configurationandactivation: Configuration and activation
Relevant signals are PMCSRn.REQSLP (n=0..5) (in SMM) and PMSWCR1.PROCMODEEN (in SMM) or assertion of ESRx (x=1..2) pins and STANDBY_CON1.SWESRSBEN or STANDBY_CON0.ESR2SBEN respectively.
Note: It is expected that the gating is active (enable = 0) during runtime
- ReqIF-WF.Type: Requirement

###### RHHA-EHGE-EGEJ-EEHE_test: Test
This mechanism is tested through LBIST (on SMM portion) and the testing mechanism stated in SM[HW]:PMS:REG_MONITOR.
- ReqIF-WF.Type: Requirement

###### RHHA-EHGE-EGEJ-EEHE_reporting: Reporting
N.A.
- ReqIF-WF.Type: Information

###### RHHA-EHGE-EGEJ-EEHE_recommendederrorreaction: Recommended error reaction
N.A.
- ReqIF-WF.Type: Information

###### QLUA-EHGE-EIIF-IDIH: SM[HW]:PMS:MONBIST
- IFX.Version: 1
- ReqIF-WF.Type: Heading

###### QLUA-EHGE-EIIF-IDIH_description: Description
The PMS provides the ability to detect structural problems of the secondary voltage monitors in PMS and detects permanent random hardware faults.
The Application SW shall trigger MONBIST at least once per driving cycle on all monitors that are used by the application.
For a detailed description of MONBIST execution, please refer to the section "Standby SMU Integration and Monitor BIST (MONBIST)" in the User Manual.
- ReqIF-WF.Type: Information

###### QLUA-EHGE-EIIF-IDIH_resetoperationalstate: Reset operational state
An LVD reset will set the configuration of this mechanism back to its default value.
- ReqIF-WF.Type: Information

###### QLUA-EHGE-EIIF-IDIH_configurationandactivation: Configuration and activation
For a detailed description of the needed configuration, please refer to the section "Standby SMU Integration and Monitor BIST (MONBIST)" in the User Manual.
- ReqIF-WF.Type: Requirement

###### QLUA-EHGE-EIIF-IDIH_test: Test
N.A.
- ReqIF-WF.Type: Requirement

###### QLUA-EHGE-EIIF-IDIH_reporting: Reporting
The result of MONBIST shall be checked by Application SW in MONBISTSTAT after the MONBIST execution is finished.
- ReqIF-WF.Type: Information

###### QLUA-EHGE-EIIF-IDIH_recommendederrorreaction: Recommended error reaction
System integrator to select appropriate safe reaction.
- ReqIF-WF.Type: Information

###### INSA-FJBF-GHBG-GHFG: SM[HW]:PMS:ENDINIT
- IFX.Version: 6 6
- ReqIF-WF.Type: Heading

###### INSA-FJBF-GHBG-GHFG_description: Description
The PMS provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – PMS (ascending offset address) in the User Manual.
- ReqIF-WF.Type: Information

###### INSA-FJBF-GHBG-GHFG_resetoperationalstate: Reset operational state
An application reset will set the configuration of this safety mechanism back to its default value.
- ReqIF-WF.Type: Information

###### INSA-FJBF-GHBG-GHFG_configurationandactivation: Configuration and activation
This safety mechanism is active after intentional configuration by application software through the PROTE register.
- ReqIF-WF.Type: Requirement

###### INSA-FJBF-GHBG-GHFG_test: Test
This safety measure can be tested after the PROT owner has been configured:
Write access to a protected register by a master agent function that is not the PROT owner.
- ReqIF-WF.Type: Requirement

###### INSA-FJBF-GHBG-GHFG_reporting: Reporting
On detection of an access protection violation the PMS will terminate the access with FPI error that is detected by the BCU, see SM[HW]:FPI:ERROR_HANDLING.
- ReqIF-WF.Type: Information

###### INSA-FJBF-GHBG-GHFG_recommendederrorreaction: Recommended error reaction
System integrator to select an appropriate safe reaction in the SMU.
- ReqIF-WF.Type: Information

###### FBGA-FJBF-GHED-FDAH: SM[HW]:PMS:SAFETY_ENDINIT
- IFX.Version: 6 6
- ReqIF-WF.Type: Heading

###### FBGA-FJBF-GHED-FDAH_description: Description
The PMS provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – PMS (ascending offset address) in the User Manual.
- ReqIF-WF.Type: Information

###### FBGA-FJBF-GHED-FDAH_resetoperationalstate: Reset operational state
An application reset will set the configuration of this safety mechanism back to its default value.
- ReqIF-WF.Type: Information

###### FBGA-FJBF-GHED-FDAH_configurationandactivation: Configuration and activation
This safety mechanism is active after intentional configuration by application software through the PROTSE register.
- ReqIF-WF.Type: Requirement

###### FBGA-FJBF-GHED-FDAH_test: Test
This safety measure can be tested after the PROT owner has been configured:
Write access to a protected register by a master agent function that is not the PROT owner.
- ReqIF-WF.Type: Requirement

###### FBGA-FJBF-GHED-FDAH_reporting: Reporting
On detection of an access protection violation the PMS will terminate the access with FPI error that is detected by the BCU, see SM[HW]:FPI:ERROR_HANDLING.
- ReqIF-WF.Type: Information

###### FBGA-FJBF-GHED-FDAH_recommendederrorreaction: Recommended error reaction
System integrator to select an appropriate safe reaction in the SMU.
- ReqIF-WF.Type: Information

###### HYWA-FJBF-GIDA-BBJD: SM[HW]:PMS:SV_AP
- IFX.Version: 1 1
- ReqIF-WF.Type: Heading

###### HYWA-FJBF-GIDA-BBJD_description: Description
Critical module registers are implemented with a write access restriction that allows access only to masters with supervisor (SV) mode privilege.
Unauthorized access attempts are blocked by this mechanism.
For a list of the registers protected by SV, see tables Register overview – access mode glossary and Register overview – PMS (ascending offset address) in the User Manual.
- ReqIF-WF.Type: Information

###### HYWA-FJBF-GIDA-BBJD_resetoperationalstate: Reset operational state
The safety mechanism is active after application reset.
- ReqIF-WF.Type: Information

###### HYWA-FJBF-GIDA-BBJD_configurationandactivation: Configuration and activation
N.A.
- ReqIF-WF.Type: Requirement

###### HYWA-FJBF-GIDA-BBJD_test: Test
This safety measure can be tested by an write access to a protected register by a master agent function without supervisor (SV) access rights.
- ReqIF-WF.Type: Requirement

###### HYWA-FJBF-GIDA-BBJD_reporting: Reporting
On detection of an access protection violation the PMS will terminate the access with FPI error that is detected by the BCU, see SM[HW]:FPI:ERROR_HANDLING.
- ReqIF-WF.Type: Information

###### HYWA-FJBF-GIDA-BBJD_recommendederrorreaction: Recommended error reaction
System integrator to select an appropriate safe reaction in the SMU.
- ReqIF-WF.Type: Information

###### ZYHA-FJBF-GIHE-GDGD: SM[HW]:PMS:CFG_AS_AP
- IFX.Version: 1 1
- ReqIF-WF.Type: Heading

###### ZYHA-FJBF-GIHE-GDGD_description: Description
The PMS checks if the access master agent function identifier is enabled for the type of access (read access and write access, configured through the PMS ACCEN registers) to the selected register.
Unauthorized access attempts are blocked by this mechanism.
- ReqIF-WF.Type: Information

###### ZYHA-FJBF-GIHE-GDGD_resetoperationalstate: Reset operational state
An application reset will set the configuration of this safety mechanism back to its default value.
- ReqIF-WF.Type: Information

###### ZYHA-FJBF-GIHE-GDGD_configurationandactivation: Configuration and activation
This safety mechanism is active after intentional configuration by application software through the ACCENx registers.
- ReqIF-WF.Type: Requirement

###### ZYHA-FJBF-GIHE-GDGD_test: Test
This safety measure can be tested after the ACCENx has been configured:
Write access to a protected register by a master agent function that is not the ACCEN owner.
- ReqIF-WF.Type: Requirement

###### ZYHA-FJBF-GIHE-GDGD_reporting: Reporting
On detection of an access protection violation the PMS terminate the access with FPI error that is detected by the BCU, see SM[HW]:FPI:ERROR_HANDLING.
- ReqIF-WF.Type: Information

###### ZYHA-FJBF-GIHE-GDGD_recommendederrorreaction: Recommended error reaction
System integrator to select an appropriate safe reaction in the SMU.
- ReqIF-WF.Type: Information

###### RHSA-FBFA-FFDF-EGBB: SM[HW]:PMS:SYNC_MONITOR
- IFX.Version: 10
- ReqIF-WF.Type: Heading

###### RHSA-FBFA-FFDF-EGBB_description: Description
Overview synchronization monitor
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The embedded DCDC regulator (EVRC) can be used in combination with external PMIC to synchronize the switching frequency.
This is needed to reduce the electromagnetic interference which can disturb the received radar data.
This can be done either by
- Case a: Capturing the PWM signal provided by PMIC with an AURIX™ internal timer module (GTM/eGTM/GPT12) and forward it to the PMS internal EVRC
- Case b: Generating a PWM signal with an AURIX™ internal timer module (GTM/eGTM/GPT12) and forward it to external PMIC DCDC aswell as the PMS internal EVRC
- Case c: Generating a PWM signal within PMS and forward it to external PMIC (DCDCSYNCO)
- Case d: Generating a PWM signal within PMS which is captured by AURIX™ internal timer module (GTM/eGTM) and forward it to PMIC DCDC
In cases a) and b) the PMS received PWM signal is checked by the Synchronization Monitor (SM[HW]:PMS:SYNC_MONITOR) to monitor if the input synchronization frequency is within a valid range. The received frequency should not extend dfmax as configured in EVRC_CON1.SYNCMAXDEV.
Note: dfmax value is application dependent
Note: For more detailed information, please refer to the “Step-down regulator (EVRC) – Input synchronization” of the PMS User Manual section.
- ReqIF-WF.Type: Information

###### RHSA-FBFA-FFDF-EGBB_resetoperationalstate: Reset operational state
This mechanism is reset by cold Power-on Reset.
- ReqIF-WF.Type: Information

###### RHSA-FBFA-FFDF-EGBB_configurationandactivation: Configuration and activation
Please refer to the “Step-down regulator (EVRC) – Input synchronization” of the PMS User Manual section for a detailed description how to configure this safety mechanism.
- ReqIF-WF.Type: Requirement

###### RHSA-FBFA-FFDF-EGBB_test: Test
The safety mechanism is tested by application software by setting the EVRC_CON3.SYNCIN=1b and EVRC_CON3.SYNCMUXSEL=00b.
These settings will force an alarm of the synchronization monitor.
Note: This latent fault test shall be executed before the connection between timer and DCDC regulator is enabled for target application
- ReqIF-WF.Type: Requirement

###### RHSA-FBFA-FFDF-EGBB_reporting: Reporting
In case of exceeding of the allowed frequency range, disappearing of the sync signal and disabling the feature, the DCDC Sync Alarm to SMU is triggered.
- ReqIF-WF.Type: Information

###### RHSA-FBFA-FFDF-EGBB_recommendederrorreaction: Recommended error reaction
Restart Lock procedure, including EVRC configuration and external PMIC configuration. If the issue continues to be apparent a cold Power-on Reset shall be executed.
- ReqIF-WF.Type: Information

###### VNPA-FBFF-HJFG-DFIJ: SM[HW]:PMS:SAFE_FSM
- IFX.Version: 2
- ReqIF-WF.Type: Heading

###### VNPA-FBFF-HJFG-DFIJ_description: Description
The state machine in the logic of the PMS is encoded using one hot coded state vectors to detect any invalid state caused by a bit-flip. Therefore any unexpected power sequence or reset generation is detected.
- ReqIF-WF.Type: Information

###### VNPA-FBFF-HJFG-DFIJ_resetoperationalstate: Reset operational state
This mechanism is reset by LVD reset.
- ReqIF-WF.Type: Information

###### VNPA-FBFF-HJFG-DFIJ_configurationandactivation: Configuration and activation
N.A.
- ReqIF-WF.Type: Requirement

###### VNPA-FBFF-HJFG-DFIJ_test: Test
N.A.
- ReqIF-WF.Type: Requirement

###### VNPA-FBFF-HJFG-DFIJ_reporting: Reporting
In case of an unintended state transition the PMS will assert a LVD reset.
- ReqIF-WF.Type: Information

###### VNPA-FBFF-HJFG-DFIJ_recommendederrorreaction: Recommended error reaction
System integrator to select appropriate safe reaction.
- ReqIF-WF.Type: Information

###### QHIA-FBFH-HBHF-DJHI: SM[HW]:PMS:SECONDARY_MONITOR
- IFX.Version: 11
- ReqIF-WF.Type: Heading

###### QHIA-FBFH-HBHF-DJHI_description: Description
Each supply rail available in a particular device is monitored by a so called secondary voltage monitor. This voltage monitor detects whether the rail voltage crosses the configured over and under voltage thresholds.
For more information about which supply rails are implemented in a particular device, and therefore which secondary monitors can be used, please refer to the PMS chapter of the User Manual, subchapter "Power supply rails and distribution"
Voltage spikes shorter than the monitoring period (4µs) would not be detected and could lead to damages and faults in the respective externally supplied domain.
Note: The monitoring period for the secondary monitors is defined through the parameter table entry "tmon".
- ReqIF-WF.Type: Information

###### QHIA-FBFH-HBHF-DJHI_resetoperationalstate: Reset operational state
This safety mechanism is reset by cold Power-on Reset.
- ReqIF-WF.Type: Information

###### QHIA-FBFH-HBHF-DJHI_configurationandactivation: Configuration and activation
For each voltage rail being used by the application, the Application Software shall enable and configure its corresponding secondary voltage monitor. To enable a secondary voltage monitor the application software shall set the registers VMONS_VxxCON.UVMOD and VMONS_VxxCON.OVMOD according to the desired detection method. To configure the threshold, the application software shall configure the registers VMONS_VxxCON.UVVAL and VMONS_VxxCON.OVVAL in accordance with the application needs, where Vxx is the name of the corresponding supply rail.
Note: The secondary voltage monitor registers inherit the name of the supply rail Vxx that the monitor is protecting. For example, the control register of the secondary voltage monitor for VDDEXT is named VMONS_VDDEXTCON.
- ReqIF-WF.Type: Requirement

###### QHIA-FBFH-HBHF-DJHI_test: Test
This mechanism is tested through MONBIST as well as through ESM[SW]:PMS:MON_REDUNDANCY.
- ReqIF-WF.Type: Requirement

###### QHIA-FBFH-HBHF-DJHI_reporting: Reporting
Upon detection of under or over voltage the monitor generates an Vxx Under/OVER Voltage Alarm to the SMU, where Vxx is the name of the corresponding supply rail.
Note: The secondary voltage monitor alarms inherit the name of the supply rail Vxx that the monitor is protecting. For example, the alarms associated with the VDDEXT secondary voltage monitor are named VDDEXT OVER voltage alarm and VDDEXT UNDER voltage alarm.
- ReqIF-WF.Type: Information

###### QHIA-FBFH-HBHF-DJHI_recommendederrorreaction: Recommended error reaction
System integrator to configure an appropriate safe reaction in SMU.
- ReqIF-WF.Type: Information

###### QKXA-FBFI-EICJ-IAJI: SM[HW]:PMS:VDDEVRSB_DET
- IFX.Version: 5
- ReqIF-WF.Type: Heading

###### QKXA-FBFI-EICJ-IAJI_description: Description
In state of the art applications it is possible that certain PMS domains are supplied by regulators of different safety integrity level. To avoid common cause failures in that case in the respective voltage domains (possible for VDDEXTDC and VDDEVRSB) a cross voltage monitoring is implemented. This is needed since the secondary voltage monitors and the LVD detectors in the respective domain for VDDEXT and VDDEVRSB might not be reliable if supplied by a regulator classified as QM.
The VDDEVRSB voltage is monitored by an LVD detector in the VDDEXTDC domain which triggers an alarm in case the VDDEVRSB drops below VLVDRSTSB. This enables the reliable measurement of voltages VDDEVRSB in case it is supplied by an external regulator classified as QM.
Additionally the VDDEXTDC voltage is monitored by an LVD detector in the VDDEVRSB voltage domain which triggers an LVD reset in case the VDDEXTDC drops below VLVDRSTDC. This enables reliable measurement and LVD reset generation in case VDDEXTDC is supplied by an external regulator classified as QM.
To validate the reference voltages of external regulators the ADC enables a measurement against the PMS internal reference voltage.
Cross Voltage Monitoring Overview
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- ReqIF-WF.Type: Information

###### QKXA-FBFI-EICJ-IAJI_resetoperationalstate: Reset operational state
This safety mechanism is active after LVD reset.
- ReqIF-WF.Type: Information

###### QKXA-FBFI-EICJ-IAJI_configurationandactivation: Configuration and activation
N.A.
- ReqIF-WF.Type: Requirement

###### QKXA-FBFI-EICJ-IAJI_test: Test
N.A.
- ReqIF-WF.Type: Requirement

###### QKXA-FBFI-EICJ-IAJI_reporting: Reporting
Upon detection of severe undervoltage condition an VDDLVDEVRSB DET Under Voltage Alarm to SMU is triggered.
- ReqIF-WF.Type: Information

###### QKXA-FBFI-EICJ-IAJI_recommendederrorreaction: Recommended error reaction
System integrator to select appropriate safe reaction.
- ReqIF-WF.Type: Information

##### FLNA-EHBJ-DIEJ-EDBG: Alarms
PMS alarms
| Alarm name | Safety mechanism | Alarm flag to be cleared in |
| --- | --- | --- |
| Vxx Under Voltage Alarm | SM[HW]:PMS:SECONDARY_MONITOR | PMS and SMU |
| Vxx OVER Voltage Alarm | SM[HW]:PMS:SECONDARY_MONITOR | PMS and SMU |
| VDDLVDEVRSB DET Under Voltage Alarm | SM[HW]:PMS:VDDEVRSB_DET | PMS and SMU |
| DCDC Sync Alarm | SM[HW]:PMS:SYNC_MONITOR | PMS and SMU |
| PMS SFF Uncorrectable Error Alarm | SM[HW]:PMS:REG_MONITOR | PMS and SMU |
| FPI error alarm | SM[HW]:PMS:SV_AP SM[HW]:PMS:CFG_AS_AP SM[HW]:PMS:ENDINIT SM[HW]:PMS:SAFETY_ENDINIT | PMS and SMU |
- IFX.Version: 1
- ReqIF-WF.Type: Information

##### RCVA-FAFF-HDCA-ACCF: External safety mechanisms
- IFX.Version: 1
- ReqIF-WF.Type: Information

###### JMYA-EHGE-CGDA-BAEF: ESM[SW]:PMS:CONFIG_READBACK
- IFX.Version: 13
- ReqIF-WF.Type: Heading

###### JMYA-EHGE-CGDA-BAEF_description: Description
The following registers of the Power Management System configuration have to be read back after write. The read back values have to be compared with the written values. In case of any difference the Application Software shall trigger a reaction.
- VMONP_VDDRST
- VMONP_VDDEXTRST
- VMONP_VSSDCHSRST
- VMONP_VDDEXTDCRST
- VMONP_VDDDCLSRST
- VMONP_VDDEVRSBRST
- VMONP_VDDMRST
- VMONP_VDDPHPHY0RST
- VMONP_VDDPHPHY1RST
- VMONP_VDDHSIFRST
- VMONP_VDDSBRST
- VMONP_VDDCPUARST
- VMONP_VDDCPUBRST
- VMONP_VDDPPURST
- VMONP_VDDPHY0RST
- VMONP_VDDPHY1RST
- VMONP_VDDCLDRST
- VMONP_VDDPHRIF0RST
- VMONP_VDDPHPHY2RST
- VMONP_VDDPHRIF1RST
- VMONP_VDDP3NVMRST
- VMONP_VDDPADRST
- VMONP_VDDLMU0RST
- VMONP_VDDLMU1RST
- VMONP_VDDPCIE1RST
- VMONP_VDDRIF0RST
- VMONP_VDDRIF1CON
- PAD_CON
- PAD_ESR2CON
- STANDBY_CON0
- RTC_CONx (x=0...2)
- DTS_CON
- VMONS_LVLSEL
- VMONS_VDDCON
- VMONS_VDDEXTCON
- VMONS_VDDEXTDCCON
- VMONS_VDDPMS0CON
- VMONS_VDDPMS1CON
- VMONS_VDDPMS2CON
- VMONS_VDDEVRSBCON
- VMONS_VDDMCON
- VMONS_VDDFLEXCON
- VMONS_VDDPHPHY0CON
- VMONS_VDDPHPHY1CON
- VMONS_VDDHSIFCON
- VMONS_VDDPHY0CON
- VMONS_VDDPHY1CON
- VMONS_VDDSBCON
- VMONS_VDDPADCON
- VMONS_VDDCPUACON
- VMONS_VDDCPUBCON
- VMONS_VDDPPUCON
- VMONS_VDDPHRIF0CON
- VMONS_VDDPHPHY2CON
- VMONS_VDDPHRIF1CON
- VMONS_VDDP3NVMCON
- VMONS_VDDSBRAMCON
- VMONS_VDDRIF0CON
- VMONS_VDDLMU0CON
- VMONS_VDDLMU1CON
- VMONS_VDDPCIE1CON
- VMONS_VDDRIF0CON
- VMONS_VDDRIF1CON
- EVRC_CONx (x = 0..5)
- EVRC_COEFFx (x = 0..5)
- ReqIF-WF.Type: Requirement

###### XFMA-EHGE-DJGH-HAHB: ESM[SW]:PMS:MON_REDUNDANCY
- IFX.Version: 1
- ReqIF-WF.Type: Heading

###### XFMA-EHGE-DJGH-HAHB_description: Description
This safety mechanism covers latent faults in the secondary voltage monitors, which implement the monitoring function for the supply generation mission function. Each secondary voltage monitor has an associated ADC, the so called “Tracking ADC”, located in the primary voltage monitors that measures the same voltage.
Note: This is not available for the monitors of VDDPMS0, VDDPMS1, VDDPMS2, VDDSBRAM and VDDFLEX
During start-up of the MCU, the application software shall read out the voltages measured by the secondary monitors and their associated tracking ADC’s from the VMONP_VxxSTAT.RESULT and VMONS_VxxSTAT.RESULT registers and compare them. Upon detection of a deviation of more than +-2% the application SW shall trigger a reaction.
During the latent fault test, the Low-Pass Filter for the tracking ADCs can be configured to the maximum value in VMONP_VxxRST.LPF and changed back afterwards.
Note:
The application software can execute this test multiple times to capture more samples for sample averaging or additional software low-pass filtering (LPF). This can be helpful if there is noise in the power supply line or in the case that either the sampling of the voltages or the readings from RESULT registers by the CPUs are performed asynchronously.
Note: In case of an under- or overvoltage the primary voltage monitors will generate an under or over voltage alarm to the SMU.
For more details about the configuration, please refer to the PMS "Secondary over- and under-Voltage monitors (VMONSx)" and PMS "Primary voltage monitors VMONPx and cold PORST" chapters in the AURIX™ TC4xx User Manual.
- ReqIF-WF.Type: Requirement

###### CJQA-EHHJ-FFFI-IHJB: ESM[HW]:SYS:WATCHDOG_FUNCTION
- IFX.Version: 11
- ReqIF-WF.Type: Heading

###### CJQA-EHHJ-FFFI-IHJB_description: Description
An external device with independent reference clock and with watchdog functionality in timeout mode supervises the AURIX™ MCU. This external device must initiate the transition to the system safe state if a fault which can lead to the violation of system safety goal is detected.
This is necessary to control common cause failures initiated by external stress conditions or internal failures of the microcontroller. This might lead to a state where the microcontroller cannot signal an internal failure.
Some systems implement program flow monitoring based on question-answer protocol with an external watchdog. In such cases, a separate timeout watchdog may not be needed.
Note: Program flow monitoring functions can be implemented with the internal watchdog timers (WDT), canceling the need for complex external watchdogs
- ReqIF-WF.Type: Information

###### CJQA-EHHJ-FFFI-IHJB_resetoperationalstate: Reset operational state
N.A.
- ReqIF-WF.Type: Information

###### CJQA-EHHJ-FFFI-IHJB_configurationandactivation: Configuration and activation
N.A.
- ReqIF-WF.Type: Requirement

###### CJQA-EHHJ-FFFI-IHJB_test: Test
N.A.
- ReqIF-WF.Type: Requirement

###### CJQA-EHHJ-FFFI-IHJB_reporting: Reporting
N.A.
- ReqIF-WF.Type: Information

###### CJQA-EHHJ-FFFI-IHJB_recommendederrorreaction: Recommended error reaction
N.A.
- ReqIF-WF.Type: Information

#### YKKA-EDEA-DBJH-JFFF: Ports
Each Port module 'Port slice' controls a set of assigned General Purpose Input Output (GPIO) port lines which are connected to pads connected to device pins or balls.
- ReqIF-WF.Type: Information

##### GRHA-FAFF-HDFI-JBJG: Internal safety mechanisms
- IFX.Version: 1
- ReqIF-WF.Type: Information

###### XICA-EHHJ-EFJF-IHBJ: SM[HW]:PORTS:ENDINIT
- IFX.Version: 1 1
- ReqIF-WF.Type: Heading

###### XICA-EHHJ-EFJF-IHBJ_description: Description
The PORTS provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – PORTS (ascending offset address) in the User Manual.
- ReqIF-WF.Type: Information

###### XICA-EHHJ-EFJF-IHBJ_resetoperationalstate: Reset operational state
An application reset will set the configuration of this safety mechanism back to its default value.
- ReqIF-WF.Type: Information

###### XICA-EHHJ-EFJF-IHBJ_configurationandactivation: Configuration and activation
This safety mechanism is active after intentional configuration by application software through the PROTE register.
- ReqIF-WF.Type: Requirement

###### XICA-EHHJ-EFJF-IHBJ_test: Test
This safety measure can be tested after the PROT owner has been configured:
Write access to a protected register by a master agent function that is not the PROT owner.
- ReqIF-WF.Type: Requirement

###### XICA-EHHJ-EFJF-IHBJ_reporting: Reporting
On detection of an access protection violation the PORTS will terminate the access with FPI error that is detected by the BCU, see SM[HW]:FPI:ERROR_HANDLING.
- ReqIF-WF.Type: Information

###### XICA-EHHJ-EFJF-IHBJ_recommendederrorreaction: Recommended error reaction
System integrator to select an appropriate safe reaction in the SMU.
- ReqIF-WF.Type: Information

###### QWXA-EHHJ-EFJG-AAAF: SM[HW]:PORTS:SAFETY_ENDINIT
- IFX.Version: 7 7
- ReqIF-WF.Type: Heading

###### QWXA-EHHJ-EFJG-AAAF_description: Description
The PORTS provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – PORTS (ascending offset address) in the User Manual.
- ReqIF-WF.Type: Information

###### QWXA-EHHJ-EFJG-AAAF_resetoperationalstate: Reset operational state
An application reset will set the configuration of this safety mechanism back to its default value.
- ReqIF-WF.Type: Information

###### QWXA-EHHJ-EFJG-AAAF_configurationandactivation: Configuration and activation
This safety mechanism is active after intentional configuration by application software through the PROTSE register.
- ReqIF-WF.Type: Requirement

###### QWXA-EHHJ-EFJG-AAAF_test: Test
This safety measure can be tested after the PROT owner has been configured:
Write access to a protected register by a master agent function that is not the PROT owner.
- ReqIF-WF.Type: Requirement

###### QWXA-EHHJ-EFJG-AAAF_reporting: Reporting
On detection of an access protection violation the PORTS will terminate the access with FPI error that is detected by the BCU, see SM[HW]:FPI:ERROR_HANDLING.
- ReqIF-WF.Type: Information

###### QWXA-EHHJ-EFJG-AAAF_recommendederrorreaction: Recommended error reaction
System integrator to select an appropriate safe reaction in the SMU.
- ReqIF-WF.Type: Information

###### TDFA-EHHJ-EFJG-JEFA: SM[HW]:PORTS:CFG_AS_AP
- IFX.Version: 4 4
- ReqIF-WF.Type: Heading

###### TDFA-EHHJ-EFJG-JEFA_description: Description
The PORTS checks if the access master agent function identifier is enabled for the type of access (read access and write access, configured through the PORTS ACCEN registers) to the selected register.
Unauthorized access attempts are blocked by this mechanism.
- ReqIF-WF.Type: Information

###### TDFA-EHHJ-EFJG-JEFA_resetoperationalstate: Reset operational state
An application reset will set the configuration of this safety mechanism back to its default value.
- ReqIF-WF.Type: Information

###### TDFA-EHHJ-EFJG-JEFA_configurationandactivation: Configuration and activation
This safety mechanism is active after intentional configuration by application software through the ACCENx registers.
- ReqIF-WF.Type: Requirement

###### TDFA-EHHJ-EFJG-JEFA_test: Test
This safety measure can be tested after the ACCENx has been configured:
Write access to a protected register by a master agent function that is not the ACCEN owner.
- ReqIF-WF.Type: Requirement

###### TDFA-EHHJ-EFJG-JEFA_reporting: Reporting
On detection of an access protection violation the PORTS terminate the access with FPI error that is detected by the BCU, see SM[HW]:FPI:ERROR_HANDLING.
- ReqIF-WF.Type: Information

###### TDFA-EHHJ-EFJG-JEFA_recommendederrorreaction: Recommended error reaction
System integrator to select an appropriate safe reaction in the SMU.
- ReqIF-WF.Type: Information

###### RMRA-EHHJ-EFJF-HFGC: SM[HW]:PORTS:SV_AP
- IFX.Version: 4 4
- ReqIF-WF.Type: Heading

###### RMRA-EHHJ-EFJF-HFGC_description: Description
Critical module registers are implemented with a write access restriction that allows access only to masters with supervisor (SV) mode privilege.
Unauthorized access attempts are blocked by this mechanism.
For a list of the registers protected by SV, see tables Register overview – access mode glossary and Register overview – PORTS (ascending offset address) in the User Manual.
- ReqIF-WF.Type: Information

###### RMRA-EHHJ-EFJF-HFGC_resetoperationalstate: Reset operational state
The safety mechanism is active after application reset.
- ReqIF-WF.Type: Information

###### RMRA-EHHJ-EFJF-HFGC_configurationandactivation: Configuration and activation
N.A.
- ReqIF-WF.Type: Requirement

###### RMRA-EHHJ-EFJF-HFGC_test: Test
This safety measure can be tested by an write access to a protected register by a master agent function without supervisor (SV) access rights.
- ReqIF-WF.Type: Requirement

###### RMRA-EHHJ-EFJF-HFGC_reporting: Reporting
On detection of an access protection violation the PORTS will terminate the access with FPI error that is detected by the BCU, see SM[HW]:FPI:ERROR_HANDLING.
- ReqIF-WF.Type: Information

###### RMRA-EHHJ-EFJF-HFGC_recommendederrorreaction: Recommended error reaction
System integrator to select an appropriate safe reaction in the SMU.
- ReqIF-WF.Type: Information

##### SFRA-EHBA-BHED-DDFJ: Alarms
PORTS alarms
| Alarm name | Safety mechanism | Alarm flag to be cleared in |
| --- | --- | --- |
| FPI error alarm | SM[HW]:PORTS:SV_AP SM[HW]:PORTS:CFG_AS_AP SM[HW]:PORTS:ENDINIT SM[HW]:PORTS:SAFETY_ENDINIT | SMU only |
- IFX.Version: 1
- ReqIF-WF.Type: Information

##### THWA-FAFF-HDFI-DFGI: External safety mechanisms
- IFX.Version: 1
- ReqIF-WF.Type: Information

###### XPIA-EHHA-GFBJ-AJDH: ESM[SW]:PORTS:GPI_REDUNDANCY
- IFX.Version: 12
- ReqIF-WF.Type: Heading

###### XPIA-EHHA-GFBJ-AJDH_description: Description
External sensor supplies identical information over two separate PCB tracks to two separate device pins of two separate ports (using “port” in the sense of GPIO functionality design part). Triggered by STM the CPU reads both values and compares them and triggers an appropriate reaction, in case of mismatch.
This ESM performs the following activities during:
1. Initialization phase (start-up)
1. Configuration of system timer for time base generation and interrupt generation
2. Initialization of PORTx
3. Initialization of PORTy
2. Run time
1. Read mission data from PORTx
2. Read monitor data from PORTy
3. Compare the redundant digital signal processing results from redundant input channels
4. In case of mismatch, application reset and repeat activity 1 and 2 (to remove soft error)
5. In case of repeat mismatch, transition to safe state
GPI redundancy
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In order to avoid common cause failures, following implementation measure shall be considered:
1. Multiple instances of PORT with separate configuration registers, state machine, logic and bus interface shall be available
2. Mission channel and monitor channel shall use two different port instances
3. Application shall not use neighboring PORTs for mission and monitor channel
- ReqIF-WF.Type: Requirement

###### PCGA-EHHA-GGCI-JEBF: ESM[SW]:PORTS:GPO_READBACK
- IFX.Version: 1
- ReqIF-WF.Type: Heading

###### PCGA-EHHA-GGCI-JEBF_description: Description
The microcontroller drives an output that operates an external actuator. The external actuator receives actuation data from the MCU and sends a feedback signal to the MCU. Alternatively, the system integrator could connect the output pin of the MCU to the input pin of the MCU.
This ESM performs the following activities during:
1. Initialization phase (start-up)
1. Initialization of PORTx
2. Initialization of PORTy
2. Run time
1. Drive actuator via PORTx
2. Read monitor data from PORTy
3. Compare or evaluate the feedback signal(Monitoring channel) from the external actuator or device against the calculated or generated output signal(Mission channel)
4. In case of mismatch, application reset and repeat activity 1 and 2 (to remove soft error)
5. In case of repeat mismatch, transition to safe state
GPO readback
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In order to avoid common cause failures, following implementation measure shall be considered:
1. Multiple instances of PORT with separate configuration registers, state machine, logic and bus interface shall be available
2. Mission channel and monitor channel shall use two different port instances
3. Application shall not use neighboring PORTs for mission and monitor channel
- ReqIF-WF.Type: Requirement

#### OIHA-EIBB-CEGE-IFCE: Parallel Processing Unit (PPU)
- IFX.Version: 4
- ReqIF-WF.Type: Information

##### QZZA-FJDE-FADE-FEIH: Internal Safety Mechanisms
- IFX.Version: 1
- ReqIF-WF.Type: Information

###### UJPA-FJGF-JGHJ-IDBH: SM[HW]:PPU:HW_REDUNDANCY
- IFX.Version: 5
- ReqIF-WF.Type: Heading

###### UJPA-FJGF-JGHJ-IDBH_description: Description
The dual-core redundancy implementation uses two identical cores (main/shadow). The outputs of both cores are compared every cycle using totally self checking comparators that feature "Level" type dual-rail error output signals.
- ReqIF-WF.Type: Information

###### UJPA-FJGF-JGHJ-IDBH_resetoperationalstate: Reset operational state
An application reset will set the configuration of this safety mechanism back to its default value.
- ReqIF-WF.Type: Information

###### UJPA-FJGF-JGHJ-IDBH_configurationandactivation: Configuration and activation
The safety mechanism must be enabled by application software. All detected errors are captured in the SFTY_ERROR_STATUS register.
Core redundancy initialization:
This sequence is used to synchronize and start the two redundant cores. The safety controller delays the reset, halt, and run signals to the two cores. Hence, after a core is reset, the initialization sequence must be performed to maintain the delay between the cores.
1. Execute a simple loop for 10 cycles to flush the core registers; an optional DSYNC can be issued to flush the pipelines.
2. Set the Password by writing 10 B to SFTY_PASSWD[1:0] register field.
3. Each core writes 10 B to the SFTY_CTRL[1:0] field requesting the safety controller to enable safety.
4. Poll for bit [2] of the SFTY_CTRL register to be set.
- ReqIF-WF.Type: Requirement

###### UJPA-FJGF-JGHJ-IDBH_test: Test
N.A.
- ReqIF-WF.Type: Requirement

###### UJPA-FJGF-JGHJ-IDBH_reporting: Reporting
The
safety monitor (in the PPU) asserts the PPU_HSSI_ERR alarm if any
mismatches are detected between the main and shadow core
outputs.
- ReqIF-WF.Type: Information

###### UJPA-FJGF-JGHJ-IDBH_recommendederrorreaction: Recommended error reaction
System integrator to select an appropriate safe reaction in the SMU.
- ReqIF-WF.Type: Information

###### ZLPA-FJGF-AJFG-FHBJ: SM[HW]:PPU:TSC_COMPARATOR
- IFX.Version: 7
- ReqIF-WF.Type: Heading

###### ZLPA-FJGF-AJFG-FHBJ_description: Description
The dual rail error output signals of each totally self checking comparator are monitored by a dual rail checker that detects the illegal values 11 B and 00 B.
- ReqIF-WF.Type: Information

###### ZLPA-FJGF-AJFG-FHBJ_resetoperationalstate: Reset operational state
This safety mechanism is automatically enabled when the parallel processing unit is booted with safety enabled.
- ReqIF-WF.Type: Information

###### ZLPA-FJGF-AJFG-FHBJ_configurationandactivation: Configuration and activation
N.A.
- ReqIF-WF.Type: Requirement

###### ZLPA-FJGF-AJFG-FHBJ_test: Test
N.A.
- ReqIF-WF.Type: Requirement

###### ZLPA-FJGF-AJFG-FHBJ_reporting: Reporting
Any illegal value of 11 B or 00 B triggers the PPU_HSSI_ERR alarm.
- ReqIF-WF.Type: Information

###### ZLPA-FJGF-AJFG-FHBJ_recommendederrorreaction: Recommended error reaction
System integrator to select an appropriate safe reaction in the SMU.
- ReqIF-WF.Type: Information

###### LCFA-FJGF-JGCA-HIAA: SM[HW]:PPU:DUAL_RAIL_SIGNALS
- IFX.Version: 4
- ReqIF-WF.Type: Heading

###### LCFA-FJGF-JGCA-HIAA_description: Description
Critical safety relevant signals are transmitted using dual-rail compare signals with complete hardware redundancy. Valid combinations are 01 B and 10 B. All other combinations are illegal values.
- ReqIF-WF.Type: Information

###### LCFA-FJGF-JGCA-HIAA_resetoperationalstate: Reset operational state
This safety mechanism is active after application reset
- ReqIF-WF.Type: Information

###### LCFA-FJGF-JGCA-HIAA_configurationandactivation: Configuration and activation
N.A.
- ReqIF-WF.Type: Requirement

###### LCFA-FJGF-JGCA-HIAA_test: Test
N.A.
- ReqIF-WF.Type: Requirement

###### LCFA-FJGF-JGCA-HIAA_reporting: Reporting
Upon detection of an error the alarm PPU_HSSI_ERR will be triggered.
- ReqIF-WF.Type: Information

###### LCFA-FJGF-JGCA-HIAA_recommendederrorreaction: Recommended error reaction
System integrator to select an appropriate safe reaction in the SMU.
- ReqIF-WF.Type: Information

###### TRDA-FJGF-JHAB-AEBH: SM[HW]:PPU:WATCHDOG_TIMER
- IFX.Version: 6
- ReqIF-WF.Type: Heading

###### TRDA-FJGF-JHAB-AEBH_description: Description
A watchdog timer with windowing capability is available for the parallel processing unit. Safety timeout signals from the watchdog timer are detected by the Safety Monitor in the PPU. The watchdog timer and windowing capability are used to monitor system signals in both the vector and scalar cores.
This safety mechanism detects deadlock situations such as pipeline lockups or incorrect application program flow.
- ReqIF-WF.Type: Information

###### TRDA-FJGF-JHAB-AEBH_resetoperationalstate: Reset operational state
An application reset will set the configuration of this safety mechanism back to its default value (disabled).
- ReqIF-WF.Type: Information

###### TRDA-FJGF-JHAB-AEBH_configurationandactivation: Configuration and activation
The application software shall configure and activate this safety mechanism before executing the safety relevant application. Please refer to the Watchdog Timer chapter in the DesignWare ARCv2 ISA Programmers' Manual for programming sequences.
- ReqIF-WF.Type: Requirement

###### TRDA-FJGF-JHAB-AEBH_test: Test
N.A.
- ReqIF-WF.Type: Requirement

###### TRDA-FJGF-JHAB-AEBH_reporting: Reporting
Upon detection of an error the alarms PPU_HSSI_ERR and PPU_WDT_TO will be triggered.
- ReqIF-WF.Type: Information

###### TRDA-FJGF-JHAB-AEBH_recommendederrorreaction: Recommended error reaction
System integrator to select an appropriate safe reaction in the SMU.
- ReqIF-WF.Type: Information

###### PFCA-FJGF-JHEB-DGDF: SM[HW]:PPU:REGISTER_EDC
- IFX.Version: 4
- ReqIF-WF.Type: Heading

###### PFCA-FJGF-JHEB-DGDF_description: Description
Internal registers (not visible to the user) of the parallel processing unit are protected with error detection code. The EDC cores are Hamming-3 codes with Single and Double Error detection capabilities. Correction of single bit errors are not supported on registers with EDC. 6-bits of EDC are added for 32-bits of data (38,32) block code.
- ReqIF-WF.Type: Information

###### PFCA-FJGF-JHEB-DGDF_resetoperationalstate: Reset operational state
This safety mechanism is active after application reset.
- ReqIF-WF.Type: Information

###### PFCA-FJGF-JHEB-DGDF_configurationandactivation: Configuration and activation
N.A.
- ReqIF-WF.Type: Requirement

###### PFCA-FJGF-JHEB-DGDF_test: Test
N.A.
- ReqIF-WF.Type: Requirement

###### PFCA-FJGF-JHEB-DGDF_reporting: Reporting
Upon detection of an EDC error the alarm PPU_HSSI_ERR will be triggered.
- ReqIF-WF.Type: Information

###### PFCA-FJGF-JHEB-DGDF_recommendederrorreaction: Recommended error reaction
System integrator to select an appropriate safe reaction in the SMU.
- ReqIF-WF.Type: Information

###### FAKA-FJGF-JHCI-DFFG: SM[HW]:PPU:REGISTER_PARITY
- IFX.Version: 6
- ReqIF-WF.Type: Heading

###### FAKA-FJGF-JHCI-DFFG_description: Description
Internal registers (not visible to the user) are protected with bit parity. One parity bit is inserted per each register byte. Parity detects single bit transient errors and also offers limited stuck-at faults coverage.
- ReqIF-WF.Type: Information

###### FAKA-FJGF-JHCI-DFFG_resetoperationalstate: Reset operational state
This safety mechanism is active after application reset.
- ReqIF-WF.Type: Information

###### FAKA-FJGF-JHCI-DFFG_configurationandactivation: Configuration and activation
N.A.
- ReqIF-WF.Type: Requirement

###### FAKA-FJGF-JHCI-DFFG_test: Test
N.A.
- ReqIF-WF.Type: Requirement

###### FAKA-FJGF-JHCI-DFFG_reporting: Reporting
Upon detection of parity errors the alarm PPU_HSSI_ERR will be triggered.
- ReqIF-WF.Type: Information

###### FAKA-FJGF-JHCI-DFFG_recommendederrorreaction: Recommended error reaction
System integrator to select an appropriate safe reaction in the SMU.
- ReqIF-WF.Type: Information

###### JBIA-FCBA-BIIB-AFJG: SM[HW]:PPU:ICACHE_ERROR_CORRECTION
The instruction cache (ICache) implements a SECDED error correction code logic to protect against errors in the data and in the address generation logic. This safety mechanism corrects single bit error and detects double bit error during read operations.
A fault in the data content stored in a SRAM can either be a single bit error or double bit error. Additional error correction code bits are calculated for the corresponding data and address bits and stored together with the data on every write access. During every read access, the error correction code bits are evaluated and in case of mismatch an error in the data or address is detected. In case of a single bit error detection in the data, it is possible to correct the error using the error correction code. Single-bit errors on address lines are treated as uncorrectable errors.
- IFX.Version: 3
- ReqIF-WF.Type: Heading

###### JBIA-FCBA-BIIB-AFJG_description: Description
- ReqIF-WF.Type: Information

###### JBIA-FCBA-BIIB-AFJG_resetoperationalstate: Reset operational state
This mechanism is active after application reset.
- ReqIF-WF.Type: Information

###### JBIA-FCBA-BIIB-AFJG_configurationandactivation: Configuration and activation
This safety mechanism is active per default. The PPU internal auxiliary register ERP_CTRL can be used to disable or enable this safety mechanism.
- ReqIF-WF.Type: Requirement

###### JBIA-FCBA-BIIB-AFJG_test: Test
The following sequence can be used to test this safety mechanism:
1. Disable exception control
2. Disable ECC protection
3. Read a memory location
4. Write corrupted data to the same location
5. Re- enable the ECC protection
6. Read the same memory location where the corrupted data had been written before
7. Re-enable exception control
For more details, please refer to the code examples provided in Code examples for PPU
- ReqIF-WF.Type: Requirement

###### JBIA-FCBA-BIIB-AFJG_reporting: Reporting
double bit error and address errors are reported on the PPU_HSSI_ERR alarm towards the SMU.
SBE are reported on the PPU_HS_SBE alarm line towards the SMU. Further SBE errors are accumulated in the hssi_sbe_counter_HS0, hssi_sbe_counter_Vision0 and hssi_cluster_sbe_counter registers.
- ReqIF-WF.Type: Information

###### JBIA-FCBA-BIIB-AFJG_recommendederrorreaction: Recommended error reaction
System integrator to select an appropriate reaction in the SMU.
- ReqIF-WF.Type: Information

###### IXUA-FCBA-DDDH-DJEB: SM[HW]:PPU:DCACHE_ERROR_CORRECTION
The data cache (DCache) implements a SECDED error correction code logic to protect against errors in the data and in the address generation logic. This safety mechanism corrects single bit error and detects double bit error during read operations.
A fault in the data content stored in a SRAM can either be a single bit error or double bit error. Additional error correction code bits are calculated for the corresponding data and address bits and stored together with the data on every write access. During every read access, the error correction code bits are evaluated and in case of mismatch an error in the data or address is detected. In case of a single bit error detection in the data, it is possible to correct the error using the error correction code. Single-bit errors on address lines are treated as uncorrectable errors.
- IFX.Version: 3
- ReqIF-WF.Type: Heading

###### IXUA-FCBA-DDDH-DJEB_description: Description
- ReqIF-WF.Type: Information

###### IXUA-FCBA-DDDH-DJEB_resetoperationalstate: Reset operational state
This mechanism is active after application reset.
- ReqIF-WF.Type: Information

###### IXUA-FCBA-DDDH-DJEB_configurationandactivation: Configuration and activation
This safety mechanism is active per default. The PPU internal auxiliary register ERP_CTRL can be used to disable or enable this safety mechanism.
- ReqIF-WF.Type: Requirement

###### IXUA-FCBA-DDDH-DJEB_test: Test
The following sequence can be used to test this safety mechanism:
1. Disable exception control
2. Disable ECC protection
3. Read a memory location
4. Write corrupted data to the same location
5. Re- enable the ECC protection
6. Read the same memory location where the corrupted data had been written before
7. Re-enable exception control
For more details, please refer to the code examples provided in Code examples for PPU
- ReqIF-WF.Type: Requirement

###### IXUA-FCBA-DDDH-DJEB_reporting: Reporting
double bit error and address errors are reported on the PPU_HSSI_ERR alarm towards the SMU.
SBE are reported on the PPU_HS_SBE alarm line towards the SMU. Further SBE errors are accumulated in the hssi_sbe_counter_HS0, hssi_sbe_counter_Vision0 and hssi_cluster_sbe_counter registers.
- ReqIF-WF.Type: Information

###### IXUA-FCBA-DDDH-DJEB_recommendederrorreaction: Recommended error reaction
System integrator to select an appropriate reaction in the SMU.
- ReqIF-WF.Type: Information

###### QLQA-FCBA-DDGE-GFEJ: SM[HW]:PPU:VDSP_ERROR_CORRECTION
The VDSP memory implements a SECDED error correction code logic to protect against errors in the data and in the address generation logic. This safety mechanism corrects single bit error and detects double bit error during read operations.
A fault in the data content stored in a SRAM can either be a single bit error or double bit error. Additional error correction code bits are calculated for the corresponding data and address bits and stored together with the data on every write access. During every read access, the error correction code bits are evaluated and in case of mismatch an error in the data or address is detected. In case of a single bit error detection in the data, it is possible to correct the error using the error correction code. Single-bit errors on address lines are treated as uncorrectable errors.
- IFX.Version: 3
- ReqIF-WF.Type: Heading

###### QLQA-FCBA-DDGE-GFEJ_description: Description
- ReqIF-WF.Type: Information

###### QLQA-FCBA-DDGE-GFEJ_resetoperationalstate: Reset operational state
This mechanism is active after application reset.
- ReqIF-WF.Type: Information

###### QLQA-FCBA-DDGE-GFEJ_configurationandactivation: Configuration and activation
This safety mechanism is active per default. The PPU internal auxiliary register ERP_CTRL can be used to disable or enable this safety mechanism.
- ReqIF-WF.Type: Requirement

###### QLQA-FCBA-DDGE-GFEJ_test: Test
The following sequence can be used to test this safety mechanism:
1. Disable exception control
2. Disable ECC protection
3. Read a memory location
4. Write corrupted data to the same location
5. Re- enable the ECC protection
6. Read the same memory location where the corrupted data had been written before
7. Re-enable exception control
For more details, please refer to the code examples provided in Code examples for PPU
- ReqIF-WF.Type: Requirement

###### QLQA-FCBA-DDGE-GFEJ_reporting: Reporting
double bit error and address errors are reported on the PPU_HSSI_ERR alarm towards the SMU.
SBE are reported on the PPU_HS_SBE alarm line towards the SMU. Further SBE errors are accumulated in the hssi_sbe_counter_HS0, hssi_sbe_counter_Vision0 and hssi_cluster_sbe_counter registers.
- ReqIF-WF.Type: Information

###### QLQA-FCBA-DDGE-GFEJ_recommendederrorreaction: Recommended error reaction
System integrator to select an appropriate reaction in the SMU.
- ReqIF-WF.Type: Information

###### ZEWA-FCBA-DFDE-HAJE: SM[HW]:PPU:CSM_ERROR_CORRECTION
The cluster shared memory (CSM) implements a SECDED error correction code logic to protect against errors in the data and in the address generation logic. This safety mechanism corrects single bit error and detects double bit error during read operations.
A fault in the data content stored in a SRAM can either be a single bit error or double bit error. Additional error correction code bits are calculated for the corresponding data and address bits and stored together with the data on every write access. During every read access, the error correction code bits are evaluated and in case of mismatch an error in the data or address is detected. In case of a single bit error detection in the data, it is possible to correct the error using the error correction code. Single-bit errors on address lines are treated as uncorrectable errors.
- IFX.Version: 3
- ReqIF-WF.Type: Heading

###### ZEWA-FCBA-DFDE-HAJE_description: Description
- ReqIF-WF.Type: Information

###### ZEWA-FCBA-DFDE-HAJE_resetoperationalstate: Reset operational state
This mechanism is active after application reset.
- ReqIF-WF.Type: Information

###### ZEWA-FCBA-DFDE-HAJE_configurationandactivation: Configuration and activation
This safety mechanism is active per default. The PPU internal auxiliary register ERP_CTRL can be used to disable or enable this safety mechanism.
- ReqIF-WF.Type: Requirement

###### ZEWA-FCBA-DFDE-HAJE_test: Test
The following sequence can be used to test this safety mechanism:
1. Disable exception control
2. Disable ECC protection
3. Read a memory location
4. Write corrupted data to the same location
5. Re- enable the ECC protection
6. Read the same memory location where the corrupted data had been written before
7. Re-enable exception control
For more details, please refer to the code examples provided in Code examples for PPU
- ReqIF-WF.Type: Requirement

###### ZEWA-FCBA-DFDE-HAJE_reporting: Reporting
double bit error and address errors are reported on the PPU_HSSI_ERR alarm towards the SMU.
SBE are reported on the PPU_HS_SBE alarm line towards the SMU. Further SBE errors are accumulated in the hssi_sbe_counter_HS0, hssi_sbe_counter_Vision0 and hssi_cluster_sbe_counter registers.
- ReqIF-WF.Type: Information

###### ZEWA-FCBA-DFDE-HAJE_recommendederrorreaction: Recommended error reaction
System integrator to select an appropriate reaction in the SMU.
- ReqIF-WF.Type: Information

###### TZEA-EHBI-JAGF-HCAD: SM[HW]:PPU:REG_MONITOR
- IFX.Version: 1
- ReqIF-WF.Type: Heading

###### TZEA-EHBI-JAGF-HCAD_description: Description
The PPU implements safety flip-flops (SFF) for detecting transient and permanent faults in the PPU configuration registers and interrupt handling logic. Safety flip-flops are special flip-flops that implement a hardware mechanism capable to detect bit flip within the flip-flops. The following registers in the PPU are implemented with SFF:
- CLC: Clock Control Register
- CTRL: PPU Control Register
- SMCTRL: PPU Safety Mechanism Control Register
- IRQSTAT: PPU Interrupt Status Register
- LCSR: Last Captured Service Request Register
- VECBASE: PPU Interrupt Vector Base Address Configuration Register
- ReqIF-WF.Type: Information

###### TZEA-EHBI-JAGF-HCAD_resetoperationalstate: Reset operational state
This safety mechanism is reset according to the reset behavior of each of the registers above, as specified in the Register Overview tables in the User Manual.
- ReqIF-WF.Type: Information

###### TZEA-EHBI-JAGF-HCAD_configurationandactivation: Configuration and activation
N. A.
- ReqIF-WF.Type: Requirement

###### TZEA-EHBI-JAGF-HCAD_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### TZEA-EHBI-JAGF-HCAD_reporting: Reporting
A fault will be reported on "PPU SFF register monitor alarm".
- ReqIF-WF.Type: Information

###### TZEA-EHBI-JAGF-HCAD_recommendederrorreaction: Recommended error reaction
System integrator to select an appropriate safe reaction in the SMU.
- ReqIF-WF.Type: Information

###### EGTA-EHCI-CHDH-DDAA: SM[HW]:PPU:SHUTDOWN_FSM
- IFX.Version: 1
- ReqIF-WF.Type: Heading

###### EGTA-EHCI-CHDH-DDAA_description: Description
To achieve a smooth power ramp down of the PPU in case of reset, a sequence of steps need to be executed. A state machine is implemented to control the execution of the necessary steps. To ensure the sequence is executed in the correct order all states are assigned with a one hot coded index. One hot encoding is referring to a group of bits where legal combinations are only those with a single high (1) bit and all others low (0). All other combinations are known as illegal states. In case of any bit change due to a random hardware fault the state machine will transition into an illegal state and will raise an alarm.
- ReqIF-WF.Type: Information

###### EGTA-EHCI-CHDH-DDAA_resetoperationalstate: Reset operational state
The safety mechanism is active from application reset on.
- ReqIF-WF.Type: Information

###### EGTA-EHCI-CHDH-DDAA_configurationandactivation: Configuration and activation
No configuration required. The mechanism is enabled automatically after reset.
- ReqIF-WF.Type: Requirement

###### EGTA-EHCI-CHDH-DDAA_test: Test
N.A.
- ReqIF-WF.Type: Requirement

###### EGTA-EHCI-CHDH-DDAA_reporting: Reporting
A fault will be reported on "PPU shutdown handling alarm".
- ReqIF-WF.Type: Information

###### EGTA-EHCI-CHDH-DDAA_recommendederrorreaction: Recommended error reaction
System integrator to select an appropriate safe reaction in the SMU.
- ReqIF-WF.Type: Information

###### YIBA-FJGE-BJJE-DJDD: SM[HW]:PPU:ENDINIT
- IFX.Version: 6
- ReqIF-WF.Type: Heading

###### YIBA-FJGE-BJJE-DJDD_description: Description
The PPU provides a unique PROT mechanism (SFR_PROT_E) that protects the configuration of the access protection mechanism (ACCEN). The ACCEN mechanism is based on the master agent function identifier. This supports freedom from interference of different SW tasks.
Unauthorized access attempts are blocked by this mechanism.
For a list of the registers protected by SFR_PROT_E, see tables Register overview – access mode glossary and Register overview – PPU (ascending offset address) in the User Manual.
- ReqIF-WF.Type: Information

###### YIBA-FJGE-BJJE-DJDD_resetoperationalstate: Reset operational state
An application reset will set the configuration of this safety mechanism back to its default value.
- ReqIF-WF.Type: Information

###### YIBA-FJGE-BJJE-DJDD_configurationandactivation: Configuration and activation
This safety mechanism is active after intentional configuration by application software through the SFR_PROT_E register.
- ReqIF-WF.Type: Requirement

###### YIBA-FJGE-BJJE-DJDD_test: Test
This safety measure can be tested after the PROT owner has been configured:
Write access to a protected register by a master agent function that is not the PROT owner.
- ReqIF-WF.Type: Requirement

###### YIBA-FJGE-BJJE-DJDD_reporting: Reporting
On detection of an access protection violation the PPU will terminate the access with SRI error that is detected by the XBAR, see SM[HW]:SRI:ERROR_HANDLING.
On detection of an access protection violation the PPU will terminate the access with LLI error that is detected by the LLI, see SM[HW]:LLI:ERROR_HANDLING.
- ReqIF-WF.Type: Information

###### YIBA-FJGE-BJJE-DJDD_recommendederrorreaction: Recommended error reaction
System integrator to select an appropriate safe reaction in the SMU.
- ReqIF-WF.Type: Information

###### LIGA-EHHA-EHJI-CABG: SM[HW]:PPU:SAFETY_ENDINIT
- IFX.Version: 7
- ReqIF-WF.Type: Heading

###### LIGA-EHHA-EHJI-CABG_description: Description
The PPU provides PROT mechanisms (SFR_PROT_SE, CSM_PROT) that protect the configuration of the access protection mechanism (ACCEN). The ACCEN mechanism is based on the master agent function identifier. This supports freedom from interference of different SW tasks.
Unauthorized access attempts are blocked by this mechanism.
For a list of the registers protected by SFR_PROT_SE and CSM_PROT, see tables Register overview – access mode glossary and Register overview – PPU (ascending offset address) in the User Manual.
- ReqIF-WF.Type: Information

###### LIGA-EHHA-EHJI-CABG_resetoperationalstate: Reset operational state
An application reset will set the configuration of this safety mechanism back to its default value.
- ReqIF-WF.Type: Information

###### LIGA-EHHA-EHJI-CABG_configurationandactivation: Configuration and activation
This safety mechanism is active after intentional configuration by application software through the SFR_PROT_SE and CSM_PROT registers.
- ReqIF-WF.Type: Requirement

###### LIGA-EHHA-EHJI-CABG_test: Test
This safety measure can be tested after the PROT owner has been configured:
Write access to a protected register by a master agent function that is not the PROT owner.
- ReqIF-WF.Type: Requirement

###### LIGA-EHHA-EHJI-CABG_reporting: Reporting
On detection of an access protection violation the PPU will terminate the access with SRI error that is detected by the XBAR, see SM[HW]:SRI:ERROR_HANDLING.
On detection of an access protection violation the PPU will terminate the access with LLI error that is detected by the LLI, see SM[HW]:LLI:ERROR_HANDLING.
- ReqIF-WF.Type: Information

###### LIGA-EHHA-EHJI-CABG_recommendederrorreaction: Recommended error reaction
System integrator to select an appropriate safe reaction in the SMU.
- ReqIF-WF.Type: Information

###### KUIA-EHHA-EHJI-DCDA: SM[HW]:PPU:SV_AP
- IFX.Version: 6
- ReqIF-WF.Type: Heading

###### KUIA-EHHA-EHJI-DCDA_description: Description
Critical module registers are implemented with a write access restriction that allows access only to masters with supervisor (SV) mode privilege.
Unauthorized access attempts are blocked by this mechanism.
For a list of the registers protected by SV see tables Register overview – access mode glossary and Register overview – PPU (ascending offset address) in the User Manual.
- ReqIF-WF.Type: Information

###### KUIA-EHHA-EHJI-DCDA_resetoperationalstate: Reset operational state
The safety mechanism is active after application reset.
- ReqIF-WF.Type: Information

###### KUIA-EHHA-EHJI-DCDA_configurationandactivation: Configuration and activation
N.A.
- ReqIF-WF.Type: Requirement

###### KUIA-EHHA-EHJI-DCDA_test: Test
This safety measure can be tested by an write access to a protected register by a master agent function without supervisor (SV) access rights.
- ReqIF-WF.Type: Requirement

###### KUIA-EHHA-EHJI-DCDA_reporting: Reporting
On detection of an access protection violation the PPU will terminate the access with SRI error that is detected by the XBAR, see SM[HW]:SRI:ERROR_HANDLING.
On detection of an access protection violation the PPU will terminate the access with LLI error that is detected by the LLI, see SM[HW]:LLI:ERROR_HANDLING.
- ReqIF-WF.Type: Information

###### KUIA-EHHA-EHJI-DCDA_recommendederrorreaction: Recommended error reaction
System integrator to select an appropriate safe reaction in the SMU.
- ReqIF-WF.Type: Information

###### PZOA-EHHA-EHJI-CFEI: SM[HW]:PPU:CFG_AS_AP
- IFX.Version: 1
- ReqIF-WF.Type: Heading

###### PZOA-EHHA-EHJI-CFEI_description: Description
The PPU checks if the access master agent function identifier is enabled for the type of access (read access and write access, configured through the PPU ACCEN registers) to the selected register.
Unauthorized access attempts are blocked by this mechanism.
- ReqIF-WF.Type: Information

###### PZOA-EHHA-EHJI-CFEI_resetoperationalstate: Reset operational state
An application reset will set the configuration of this safety mechanism back to its default value.
- ReqIF-WF.Type: Information

###### PZOA-EHHA-EHJI-CFEI_configurationandactivation: Configuration and activation
This safety mechanism is active after intentional configuration by application software through the ACCENx registers.
- ReqIF-WF.Type: Requirement

###### PZOA-EHHA-EHJI-CFEI_test: Test
This safety measure can be tested after the ACCENx has been configured:
Write access to a protected register by a master agent function that is not the ACCEN owner.
- ReqIF-WF.Type: Requirement

###### PZOA-EHHA-EHJI-CFEI_reporting: Reporting
On detection of an access protection violation the PPU will terminate the access with SRI error that is detected by the XBAR, see SM[HW]:SRI:ERROR_HANDLING.
On detection of an access protection violation the PPU will terminate the access with LLI error that is detected by the LLI, see SM[HW]:LLI:ERROR_HANDLING.
- ReqIF-WF.Type: Information

###### PZOA-EHHA-EHJI-CFEI_recommendederrorreaction: Recommended error reaction
System integrator to select an appropriate safe reaction in the SMU.
- ReqIF-WF.Type: Information

##### EWBA-EHBJ-DJAI-FCHA: Alarms
PPU alarms
| Alarm name | Safety mechanism | Alarm flag to be cleared in |
| --- | --- | --- |
| PPU_WDT_TO (PPU watchdog timer timeout) | SM[HW]:PPU:WATCHDOG_TIMER | PPU and SMU |
| PPU_HSSI_ERR (PPU safety monitor alarm) | SM[HW]:PPU:DUAL_RAIL_SIGNALS SM[HW]:PPU:HW_REDUNDANCY SM[HW]:PPU:REGISTER_PARITY SM[HW]:PPU:REGISTER_EDC SM[HW]:PPU:TSC_COMPARATOR SM[HW]:PPU:ICACHE_ERROR_DETECTION SM[HW]:PPU:DCACHE_ERROR_DETECTION SM[HW]:PPU:VDSP_ERROR_DETECTION SM[HW]:PPU:CSM_ERROR_DETECTION | PPU and SMU |
| PPU_HS_SBE (PPU single bit error alarm) | SM[HW]:PPU:ICACHE_ERROR_DETECTION SM[HW]:PPU:DCACHE_ERROR_DETECTION SM[HW]:PPU:VDSP_ERROR_DETECTION SM[HW]:PPU:CSM_ERROR_DETECTION | SMU only |
| PPU SFF register monitor alarm | SM[HW]:PPU:REG_MONITOR | SMU only |
| PPU shutdown handling alarm | SM[HW]:PPU:SHUTDOWN_FSM | SMU only |
| SRI XBAR Bus Error Event Alarm | SM[HW]:PPU:SV_AP SM[HW]:PPU:CFG_AS_AP SM[HW]:PPU:ENDINIT SM[HW]:PPU:SAFETY_ENDINIT | SMU only |
| SRI S2L Address Phase ECC Error Alarm | SM[HW]:PPU:SV_AP SM[HW]:PPU:CFG_AS_AP SM[HW]:PPU:ENDINIT SM[HW]:PPU:SAFETY_ENDINIT | SMU only |
Note: For clearing alarms in the PPU please see watchdog timer and safety feature section in the DesignWare ARCv2 ISA Programmers' Manual.
- IFX.Version: 1
- ReqIF-WF.Type: Information

##### OURA-FJDE-FADH-CFEG: External Safety Mechanisms
- IFX.Version: 1
- ReqIF-WF.Type: Information

###### PFZA-EHDF-JCAJ-FCGF: ESM[SW]:PPU:SHUTDOWN_REQUEST
- IFX.Version: 8
- ReqIF-WF.Type: Heading

###### PFZA-EHDF-JCAJ-FCGF_description: Description
Application Software shall detect random HW
faults that lead to unintended shutdown requests by checking the
operational status of PPU through the status bit SD in the PPU
special function register (SFR) STAT once per fault tolerant time
interval (FTTI). If the value read from the status bit SD is
different than the reset value, then a failure is detected. Upon
detection of a failure, application software shall trigger a safe
reaction. In case of first occurrence a possible reaction is to
restart the PPU application software at a defined state. In case of
multiple consecutive concurrences consider the PPU as not available
for the application.
- ReqIF-WF.Type: Requirement

###### GWHA-FAGI-FHAC-JFJF: ESM[SW]:PPU:CONFIG_READBACK
- IFX.Version: 4
- ReqIF-WF.Type: Heading

###### GWHA-FAGI-FHAC-JFJF_description: Description
- ReqIF-WF.Type: Requirement

###### GWHA-FAGI-FHAC-JFJF_section2
The application software shall detect missing writes to configuration registers by reading them back after configuration and comparing the read values with the expected values. Upon detection of a mismatch, the application software shall trigger a safe reaction.
The following registers of the PPU configuration have to be read back after configuration:
- PROT registers
- ACCEN registers
- CLC: Clock control register
- CTRL: PPU control register
- SMCTRL: PPU safety mechanism control register
- VECBASE: PPU interrupt vector base address configuration register
- ReqIF-WF.Type: Information

###### SOXA-FBGC-IEGJ-BJBH: ESM[SW]:PPU:BUS_ERROR_HANDLING
- IFX.Version: 5
- ReqIF-WF.Type: Heading

###### SOXA-FBGC-IEGJ-BJBH_description: Description
- ReqIF-WF.Type: Requirement

###### SOXA-FBGC-IEGJ-BJBH_section2
The application shall detect bus errors on the LLI which are caused by unsuccessful transactions (reads or writes) from the PPU LBU master interface to addresses in segment 0xE of the system address map. Examples of unsuccessful transactions are accesses to non-existing addresses or violation of the access protection mechanisms (for example SAFETY_ENDINIT, CFG_AS_AP, etc.) implemented in the LLI slave interfaces. Such unsuccessful transactions will be notified by the LLI back to the PPU’s exception handler [bus error from data memory; vector offset 0x04; vector number 0x01; cause code 0x10]. The system integrator shall program the mentioned PPU exception handler to read the Exception Fault Address (EFA) register upon assertion. If the address read out of EFA register belongs to the 0xE segment of the system address map, then an error is detected. Upon detection of such a bus error, the application software shall trigger a safe reaction.
Note: Unsuccessful transactions due to transaction integrity errors are handled by SM[HW]:LLI:TRANSACTION_INTEGRITY and have dedicated alarms.
Tip: Detailed information about the EFA register can be found in the DesignWare ARCv2 ISA Programmers' Manual.
- ReqIF-WF.Type: Information

###### JVPA-FJGF-AAAJ-CAEF: ESM[SW]:PPU:STL
- IFX.Version: 7
- ReqIF-WF.Type: Heading

###### JVPA-FJGF-AAAJ-CAEF_description: Description
The application software shall execute the software self test libraries (STL) once every diagnostic test time interval to detect permanent faults in the vector digital signal processing unit of the parallel processing unit. Software test libraries are diagnostic tests based on fault injection that are created for the VDSP unit of the PPU.
The STLs are self-checking, that is, whenever the STL detects an error, it will report it in the SFTY_ERROR_STATUS register and it will raise the PPU_HSSI_ERR alarm.
If a fault is present at the point in time in which this safety mechanism is executed, it will detect the fault and report it within 10 ms.
The system integrator shall use the STLs version: <t.b.d.>
Note: the STL can be obtained directly from Synopsys®: www.synopsys.com
- ReqIF-WF.Type: Requirement

#### HBSA-EDCJ-DCJC-AACF: Queued Synchronous Peripheral Interface (QSPI)
QSPI provides synchronous serial communication with external devices using clock, data-in, data-out, and slave select signals. Operation as both master and slave, with flexible configurations and timing options are also supported.
- ReqIF-WF.Type: Information

##### XFWA-FAFF-HFEG-DFHJ: Internal safety mechanisms
- IFX.Version: 1
- ReqIF-WF.Type: Information

###### EDXA-EHHJ-EGGI-CFEB: SM[HW]:QSPI:ENDINIT
- IFX.Version: 1 1
- ReqIF-WF.Type: Heading

###### EDXA-EHHJ-EGGI-CFEB_description: Description
The QSPI provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – QSPI (ascending offset address) in the User Manual.
- ReqIF-WF.Type: Information

###### EDXA-EHHJ-EGGI-CFEB_resetoperationalstate: Reset operational state
An application reset will set the configuration of this safety mechanism back to its default value.
- ReqIF-WF.Type: Information

###### EDXA-EHHJ-EGGI-CFEB_configurationandactivation: Configuration and activation
This safety mechanism is active after intentional configuration by application software through the PROTE register.
- ReqIF-WF.Type: Requirement

###### EDXA-EHHJ-EGGI-CFEB_test: Test
This safety measure can be tested after the PROT owner has been configured:
Write access to a protected register by a master agent function that is not the PROT owner.
- ReqIF-WF.Type: Requirement

###### EDXA-EHHJ-EGGI-CFEB_reporting: Reporting
On detection of an access protection violation the QSPI will terminate the access with FPI error that is detected by the BCU, see SM[HW]:FPI:ERROR_HANDLING.
- ReqIF-WF.Type: Information

###### EDXA-EHHJ-EGGI-CFEB_recommendederrorreaction: Recommended error reaction
System integrator to select an appropriate safe reaction in the SMU.
- ReqIF-WF.Type: Information

###### DUFA-EHHJ-EGGI-DHCA: SM[HW]:QSPI:SAFETY_ENDINIT
- IFX.Version: 1 1
- ReqIF-WF.Type: Heading

###### DUFA-EHHJ-EGGI-DHCA_description: Description
The QSPI provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – QSPI (ascending offset address) in the User Manual.
- ReqIF-WF.Type: Information

###### DUFA-EHHJ-EGGI-DHCA_resetoperationalstate: Reset operational state
The PROTSE mechanism is active after intentional configuration by application software.
- ReqIF-WF.Type: Information

###### DUFA-EHHJ-EGGI-DHCA_configurationandactivation: Configuration and activation
This safety mechanism is active after intentional configuration by application software through the PROTSE register.
- ReqIF-WF.Type: Requirement

###### DUFA-EHHJ-EGGI-DHCA_test: Test
This safety measure can be tested after the PROT owner has been configured:
Write access to a protected register by a master agent function that is not the PROT owner.
- ReqIF-WF.Type: Requirement

###### DUFA-EHHJ-EGGI-DHCA_reporting: Reporting
On detection of an access protection violation the QSPI will terminate the access with FPI error that is detected by the BCU, see SM[HW]:FPI:ERROR_HANDLING.
- ReqIF-WF.Type: Information

###### DUFA-EHHJ-EGGI-DHCA_recommendederrorreaction: Recommended error reaction
System integrator to select an appropriate safe reaction in the SMU.
- ReqIF-WF.Type: Information

###### ZGSA-EHHJ-EGGI-DBDA: SM[HW]:QSPI:CFG_AS_AP
- IFX.Version: 4 4
- ReqIF-WF.Type: Heading

###### ZGSA-EHHJ-EGGI-DBDA_description: Description
The QSPI checks if the access master agent function identifier is enabled for the type of access (read access and write access, configured through the QSPI ACCEN registers) to the selected register.
Unauthorized access attempts are blocked by this mechanism.
- ReqIF-WF.Type: Information

###### ZGSA-EHHJ-EGGI-DBDA_resetoperationalstate: Reset operational state
An application reset will set the configuration of this safety mechanism back to its default value.
- ReqIF-WF.Type: Information

###### ZGSA-EHHJ-EGGI-DBDA_configurationandactivation: Configuration and activation
This safety mechanism is active after intentional configuration by application software through the ACCENx registers.
- ReqIF-WF.Type: Requirement

###### ZGSA-EHHJ-EGGI-DBDA_test: Test
This safety measure can be tested after the ACCENx has been configured:
Write access to a protected register by a master agent function that is not the ACCEN owner.
- ReqIF-WF.Type: Requirement

###### ZGSA-EHHJ-EGGI-DBDA_reporting: Reporting
On detection of an access protection violation the QSPI terminate the access with FPI error that is detected by the BCU, see SM[HW]:FPI:ERROR_HANDLING.
- ReqIF-WF.Type: Information

###### ZGSA-EHHJ-EGGI-DBDA_recommendederrorreaction: Recommended error reaction
System integrator to select an appropriate safe reaction in the SMU.
- ReqIF-WF.Type: Information

###### AMAA-EHHJ-EGGI-JGHD: SM[HW]:QSPI:SV_AP
- IFX.Version: 4 4
- ReqIF-WF.Type: Heading

###### AMAA-EHHJ-EGGI-JGHD_description: Description
Critical module registers are implemented with a write access restriction that allows access only to masters with supervisor (SV) mode privilege.
Unauthorized access attempts are blocked by this mechanism.
For a list of the registers protected by SV, see tables Register overview – access mode glossary and Register overview – QSPI (ascending offset address) in the User Manual.
- ReqIF-WF.Type: Information

###### AMAA-EHHJ-EGGI-JGHD_resetoperationalstate: Reset operational state
The safety mechanism is active after application reset.
- ReqIF-WF.Type: Information

###### AMAA-EHHJ-EGGI-JGHD_configurationandactivation: Configuration and activation
N.A.
- ReqIF-WF.Type: Requirement

###### AMAA-EHHJ-EGGI-JGHD_test: Test
This safety measure can be tested by an write access to a protected register by a master agent function without supervisor (SV) access rights.
- ReqIF-WF.Type: Requirement

###### AMAA-EHHJ-EGGI-JGHD_reporting: Reporting
On detection of an access protection violation the QSPI will terminate the access with FPI error that is detected by the BCU, see SM[HW]:FPI:ERROR_HANDLING.
- ReqIF-WF.Type: Information

###### AMAA-EHHJ-EGGI-JGHD_recommendederrorreaction: Recommended error reaction
System integrator to select an appropriate safe reaction in the SMU.
- ReqIF-WF.Type: Information

##### DNMA-EHBJ-DGEI-BGGA: Alarms
QSPI alarms
| Alarm name | Safety mechanism | Alarm flag to be cleared in |
| --- | --- | --- |
| FPI error alarm | SM[HW]:QSPI:SV_AP SM[HW]:QSPI:CFG_AS_AP SM[HW]:QSPI:ENDINIT SM[HW]:QSPI:SAFETY_ENDINIT | SMU only |
- IFX.Version: 1
- ReqIF-WF.Type: Information

##### MJPA-FAFF-HFEG-IFCI: External safety mechanisms
- IFX.Version: 1
- ReqIF-WF.Type: Information

###### KZGA-FJBE-HHIF-IGED: ESM[SW]:QSPI:SAFE_COMMUNICATION
- IFX.Version: 1
- ReqIF-WF.Type: Heading

###### KZGA-FJBE-HHIF-IGED_description: Description
Random hardware faults in the communication controller or in the communication interface can lead to corruption or loss of safety related data carried by a communication frame. In-order to detect the causes or effects of such communication faults, the application software has to implement safe End-to-End communication protecting the safety critical data.
The Safe End-to-End communication has to be implemented by application software of both the sender and the receiver of a communication frame. The sender appends an "E2E header" containing safety elements such as CRC or Counter to the communication data. The receivers evaluates the safety elements contained in the E2E header of the communication frame in order to detect faults. Figure below shows an example layout and construction of a communication frame protected by Safe End-to-End communication.
Safe end-to-end communication
The following section describes the safety elements contained in the E2E header
Cyclic redundancy check (CRC)
The CRC is calculated by the sender for the contents of the safety critical communication data. The CRC protects against data corruption. The user is responsible for choosing an appropriate CRC polynomial with sufficient Hamming distance to provide required error detection capability for a corresponding length of communication data. It is recommended to use a different CRC polynomial 1than the one used by the communication controller (if any) to provide redundancy. The receiver evaluates the CRC in the E2E header of the received communication frame to detect data corruption. A mismatch of the computed CRC value compared to the received CRC value indicates occurrence of data corruption.
1Hint: AUTOSAR Specification of SW-C End-to-End Communication Protection Library Release 4.3.1 recommends CRC polynomials to be used for various length of application data.
Counter
The Counter enables to detect faults such as loss of data, repetition of data. The sender for a given application data, inserts a counter value into the E2E header. The counter value is incremented for every transmission of the application data. The receiver evaluates the counter value in the E2E header of the received communication frame with an expected counter value. The following error scenarios can be detected:
- Repetition of frame - The received counter values is same as that of the previous counter value
- Loss of frame(s) - The received counter value is non–consecutive
The receiver upon successful evaluation of the received communication frame increments the corresponding current counter value.
Note: The user is responsible for implementing counter synchronization methods between the sender and receiver.
The application software can combine the counter value with a timer to detect delayed communication or block in the communication interface. Example: a timer (for example the system timer (STM)) can be configured to trigger a periodic check of the counter value of the associated application data. If the counter value does not change for a given time interval (for example within an FTTI), then delayed communication or block in communication is detected.
- ReqIF-WF.Type: Requirement

###### XBHA-FJBE-GEHB-JDII: ESM[SW]:QSPI:CHANNEL_REDUNDANCY
- IFX.Version: 1
- ReqIF-WF.Type: Heading

###### XBHA-FJBE-GEHB-JDII_description: Description
Faults in the following functions of QSPI can be detected by implementing SPI communication over 2 independent channels triggered by independent transmit triggers
- Transmit: The QSPI receives data from application software and sends it to an external SPI device
- Transmit Trigger: The QSPI initiates transmission of SPI frame upon a trigger from GTM or eGTM
- Receive: The QSPI receives data from an external SPI device and routes it to application software for further processing
The figure below shows an illustration for implementing a redundant QSPI communication channel. One of the redundant SPI communication channel can be assigned as "Mission" channel (highlighted in Blue) and the other can be used as a "Monitoring" channel (highlighted in green)
QSPI channel redundancy
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In-order to prevent common cause faults, the redundant QSPI communication channels have to be independent of each other. This can be achieved by:
- Using separate QSPI modules as Mission and Monitoring communication channel
- Both channels need to have similar configuration
- Other supporting blocks (for example PORTS) need to be configured similarly to enable the communication, for example driver strength and pull-up
- Using independent transmit trigger sources from GTM or eGTM for the mission and monitoring communication channel
- Using independent package pins and PORTS instances
Please refer to the chapter “Safety related information for package” of the safety manual to find out which pins and modules are independent of each other.
Reception of data
As soon as one of the channels receives a frame a synchronization mechanism needs to be triggered. If this synchronization identifies two matching packets, then the lockstep CPU needs to compare the packet content. If the content of Mission- and Monitoring channel match within an FTTI, then the data is considered as safe. The data comparison may optionally contain application level plausibility checks on result value bounds.
Possible synchronization techniques are:
1. Flag based synchronization
On receiving a frame a corresponding flag is set (Mission flag or Monitoring flag)
- If both flags are set within FTTI, then synchronization is OK. This situation will trigger frame comparison and flag reset
- If only one flag is set at the end of FTTI and the corresponding channel receives another packet, this is an error
2. Packet number
On receiving a frame a corresponding counter is increased (Mission counter or Monitoring counter)
- If the counters match within FTTI, then synchronization is OK and a comparison can be triggered
- If the counters have a difference greater than one at the end of FTTI, then an error has occurred
3. Timestamp from system timer
Each channel features a timestamp variable (Mission timestamp or Monitoring timestamp) stored on safe memory (for example DSPR).
- Both timestamp variables are initialized with a value equal to zero
- On receiving a frame the corresponding timestamp variables (Mission timestamp and Monitoring timestamp) are updated from a safe timer (for example System Timer (STM))
- As soon as both timestamp variables are different to zero a comparison by lockstep CPU of frame data and time window is triggered. This also sets both timestamp variables to zero
- If a channel receives a frame and its corresponding timestamp variable is not zero, then an error is detected
- If the timestamp variable values differ by more than a predefined time window, then an error is detected
- The system integrator shall ensure that the timestamp variables are checked at least once per FTTI, either with a periodic trigger or by ensuring that the message rate is at least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
Upon detection of an error the application software shall trigger an appropriate reaction.
Transmission of data
The application SW prepares frames containing the same data on Mission and Monitoring channel. Then both channels are triggered.
Interrupts
If the application software uses interrupts of QSPI to service the mission and monitoring channel then to detect missing or unintended interrupts, the application software shall check if the interrupts arriving from mission channel are also arriving from the monitoring channel within an FTTI. If the presence of only one of the interrupts is detected at end of the FTTI, the application software shall trigger an error signal and an appropriate reaction.
- ReqIF-WF.Type: Requirement

###### XZMA-FJBE-HIAC-GIEH: ESM[SW]:QSPI:SAFE_DEVICE_CONFIGURATION
- IFX.Version: 10
- ReqIF-WF.Type: Heading

###### XZMA-FJBE-HIAC-GIEH_description: Description
Random hardware faults in the communication controller or in the communication interface can lead to corruption or loss of safety related configuration data sent over SPI from the AURIX™ microcontroller to the external safety relevant device.
The application software running in the AURIX™ microcontroller shall implement the safe configuration protocol as specified in the safety documentation of the external safety relevant device. Upon detection of a communication error, the application software shall trigger a safe reaction.
Note: The system integrator is responsible of choosing an external safety relevant device that features a safe configuration protocol which offers sufficient coverage for the ASIL requirements of the application.
The safe configuration protocol shall cover the following potential failures:
- Corruption of configuration data
- Loss of configuration data
For example:
The Infineon Technologies AG OPTIREG™ Power Management IC (PMIC) device features an SPI communication protocol that enables detection of configuration data corruption (parity bit or CRC). Additionally, the device requires the application software to implement a write-and-verify mechanism that allows detection of data loss.
- ReqIF-WF.Type: Requirement

###### SUFA-EHHE-GBCH-BIBI: ESM[SW]:QSPI:ISR_MONITOR
- IFX.Version: 6
- ReqIF-WF.Type: Heading

###### SUFA-EHHE-GBCH-BIBI_description: Description
This ESM shall detect missing or unintended interrupts originating from the QSPI module. Usage of interrupts in this FB depends on the use cases and code implementation.
Transmit/Receive interrupts
The QSPI module signals to the application software that a message was received by triggering the interrupts RXFIFO, PT1, PT2 and U. Similarly, a transmitted message is signaled by triggering the interrupts TXFIFO, PT1, PT2 and U. To detect individual missing or unintended transmit or receive interrupts, the system integrator shall use the properties of the safe E2E communication (e.g. timestamp or frame counter). For example, a repeated receive frame counter value indicates that an unintended receive interrupt has occurred. Interrupts missing altogether are covered by the timeout mechanism of the safe E2E communication.
Upon detection of a missing or unintended interrupt, the application software shall trigger an appropriate reaction.
Other interrupts
Other interrupts originating from the QSPI module can be used if the system integrator wishes to do so. These are: ERR (all flags). Errors in the communication due to unintended or missing interrupts of this type are also covered by safe E2E communication.
Unused interrupts:
If the system integrator decides not to use certain interrupts, these shall be disabled in the GLOBALCON1 and BACON register(s) and in the interrupt router SRC register.
- ReqIF-WF.Type: Requirement

#### YATA-FJDJ-FDCF-AAAF: Radar Direct Memory Access (RDMA)
The Radar DMA transfers Radar data samples from a source memory location to a destination memory location without direct CPU involvement.
- IFX.Version: 1
- ReqIF-WF.Type: Information

##### YQWA-FAFF-HGIC-JJDB: Internal safety mechanisms
- IFX.Version: 1
- ReqIF-WF.Type: Information

###### PRWA-FBDB-GADI-EAJD: SM[HW]:RDMA:REDUNDANCY
- IFX.Version: 1
- ReqIF-WF.Type: Heading

###### PRWA-FBDB-GADI-EAJD_description: Description
The redundancy detects permanent and transient faults in the operation of a hardware element. Two symmetrical hardware modules perform duplicate operations and the results are compared. Any mismatch results in an error condition.
A hardware based self-test detects latent faults in the redundancy mechanism and a software based test detects latent faults in the alarm.
The RDMA uses control and datapath redundancy to cover the logic that is not covered by SM[HW]:RDMA:ACTIVE_CFG_CHECK, SM[HW]:RDMA:ACTIVE_CFG_CHECK_SCC, SM[HW]:IR:ICU_MONITOR, SM[HW]:FPI:FPI_TRANSACTION_INTEGRITY, SM[HW]:SRI:SRI_TRANSACTION_INTEGRITY or SM[HW]:RDMA:SEP_TRANSACTION_INTEGRITY.
- ReqIF-WF.Type: Information

###### PRWA-FBDB-GADI-EAJD_resetoperationalstate: Reset operational state
This safety mechanism is enabled after application reset.
- ReqIF-WF.Type: Information

###### PRWA-FBDB-GADI-EAJD_configurationandactivation: Configuration and activation
N.A.
- ReqIF-WF.Type: Requirement

###### PRWA-FBDB-GADI-EAJD_test: Test
The redundancy compare function provides the application software with the ability to generate an alarm by setting the redundantly encoded CHc_SM_USER.CREDTST = ON. This will inject an error into the comparators until it is set to OFF.
The following faults will be detected:
- A stuck at fault on the alarm signal path
- ReqIF-WF.Type: Requirement

###### PRWA-FBDB-GADI-EAJD_reporting: Reporting
If this safety mechanism detects a fault, the RDMA generates a RDMA redundancy mismatch alarm.
- ReqIF-WF.Type: Information

###### PRWA-FBDB-GADI-EAJD_recommendederrorreaction: Recommended error reaction
System integrator to select appropriate safe reaction in SMU.
- ReqIF-WF.Type: Information

###### ESCA-FBDB-GDDJ-FFAJ: SM[HW]:RDMA:ACTIVE_CFG_CHECK
- IFX.Version: 1
- ReqIF-WF.Type: Heading

###### ESCA-FBDB-GDDJ-FFAJ_description: Description
The RDMA channel configuration checksum is a cyclic redundancy checksum calculated for the active RDMA channel configuration data. The RDMA periodically calculates an RDMA channel configuration checksum for the active RDMA channel. On completion of the calculation, the RDMA compares the calculated RDMA channel configuration checksum with an expected RDMA channel configuration checksum stored in CHc_SM_REGCRC.CRC. If the calculated and expected RDMA channel configuration checksums do not match, the RDMA triggers an alarm.
The register CRC uses a 32 bit Ethernet polynomial as defined in the IEEE 802.3 standard which assumes that the register contents are converted to an LSB first sequential data stream. The data stream is generated using the registers of the active RDMA channel. Additionally, the value of following registers and bit-fields are assumed to be 0 H for calculating the reference CRC.
- All unused register addresses
- All reserved bit-fields
- All write-only bit-fields
- CHc_CTRL_TSR.RST
- CHc_CTRL_TSR.TRL
- CHc_CTRL_TSR.HLTREQ
- CHc_CTRL_TSR.HLTACK
- CHc_CTRL_TSR.ISTSC
- CHc_CTRL_TSR.ISTSB
- CHc_CTRL_TRIGSTAT
- CHc_CTRL_REGCRC
- ReqIF-WF.Type: Information

###### ESCA-FBDB-GDDJ-FFAJ_resetoperationalstate: Reset operational state
This safety mechanism is reset and disabled by module reset and RDMA channel reset.
- ReqIF-WF.Type: Information

###### ESCA-FBDB-GDDJ-FFAJ_configurationandactivation: Configuration and activation
The RDMA channel configuration checksum is enabled by writing CHc_SM_CTRL.REGCRCEN to ON and disabled by writing OFF.
- ReqIF-WF.Type: Requirement

###### ESCA-FBDB-GDDJ-FFAJ_test: Test
This safety mechanism can be tested by writing an invalid CRC to CHc_SM_REGCRC.CRC.
- ReqIF-WF.Type: Requirement

###### ESCA-FBDB-GDDJ-FFAJ_reporting: Reporting
If the RDMA channel configuration checksum comparison fails, the RDMA generates an RDMA configuration mismatch alarm.
- ReqIF-WF.Type: Information

###### ESCA-FBDB-GDDJ-FFAJ_recommendederrorreaction: Recommended error reaction
System integrator to select appropriate safe reaction in SMU.
- ReqIF-WF.Type: Information

###### YKDA-FCCF-HIHF-GEGC: SM[HW]:RDMA:ACTIVE_CFG_CHECK_SCC
- IFX.Version: 1
- ReqIF-WF.Type: Heading

###### YKDA-FCCF-HIHF-GEGC_description: Description
The active configuration check has to sequence through states to read each configuration register and then compare the resulting CRC over the registers with the expected value. This sequential logic is duplicated and its state compared with the state in the duplicate. A fault is detected when the state differs.
- ReqIF-WF.Type: Information

###### YKDA-FCCF-HIHF-GEGC_resetoperationalstate: Reset operational state
This safety mechanism is enabled after application reset.
- ReqIF-WF.Type: Information

###### YKDA-FCCF-HIHF-GEGC_configurationandactivation: Configuration and activation
N.A.
- ReqIF-WF.Type: Requirement

###### YKDA-FCCF-HIHF-GEGC_test: Test
N.A.
- ReqIF-WF.Type: Requirement

###### YKDA-FCCF-HIHF-GEGC_reporting: Reporting
If this safety mechanism detects a fault, the RDMA generates an RDMA configuration mismatch alarm.
- ReqIF-WF.Type: Information

###### YKDA-FCCF-HIHF-GEGC_reaction: Reaction
System integrator to select appropriate safe reaction in SMU.
- ReqIF-WF.Type: Information

###### NKTA-FBDB-GDEE-GDBH: SM[HW]:RDMA:SEP_TRANSACTION_INTEGRITY
- IFX.Version: 17
- ReqIF-WF.Type: Heading

###### NKTA-FBDB-GDEE-GDBH_description: Description
The M_SEP interface implements redundancy and EDC mechanisms to ensure transaction integrity.
- All request, acknowledge and error signals are redundantly encoded with an inverted parity. The RMEM generates an alarm if it detects a parity error on the request signals. The RDMA generates an alarm if it detects a parity error on the acknowledge or error signals
- On read accesses, the RMEM generates an EDC covering the read address and data. The generated EDC is transmitted to the RDMA along with the read address and data. The RDMA performs an EDC check on the received read address and data and generates an alarm if the check fails
- ReqIF-WF.Type: Information

###### NKTA-FBDB-GDEE-GDBH_resetoperationalstate: Reset operational state
This safety mechanism is enabled and active after module reset.
- ReqIF-WF.Type: Information

###### NKTA-FBDB-GDEE-GDBH_configurationandactivation: Configuration and activation
N.A.
- ReqIF-WF.Type: Requirement

###### NKTA-FBDB-GDEE-GDBH_test: Test
This safety mechanism can be tested by
- Setting bit-field SM_USER.RMCTST to ON (10 B) and executing an operation which results in the RDMA generating a request to the RMEM
- The RDMA inserts a parity error on the request signals to the RMEM, which in turn results in the RMEM generating an SEP error alarm
- The RDMA generates an SEP transaction integrity alarm if it detects an invalid encoding in the SM_USER.RMCTST bit-field
- Setting RMEM bit-field SM_USER.RDEDCTST to ON (10 B) and executing an operation which results in the RDMA generating a read request to the RMEM
- The RDMA inserts a EDC error on the read response from the RMEM, which results in the RDMA generating a RDMA SEP transaction integrity alarm
- The RDMA generates an SEP transaction integrity alarm if it detects an invalid encoding in the SM_USER.RDEDCTST bit-field
- ReqIF-WF.Type: Requirement

###### NKTA-FBDB-GDEE-GDBH_reporting: Reporting
On detection of a parity or EDC violation on the M_SEP interface between the RDMA and RMEM, the RDMA generates a SEP transaction integrity alarm.
- ReqIF-WF.Type: Information

###### NKTA-FBDB-GDEE-GDBH_recommendederrorreaction: Recommended error reaction
System integrator to select appropriate safe reaction in SMU.
- ReqIF-WF.Type: Information

###### ZZMA-FBDB-FIAH-CIEI: SM[HW]:RDMA:CFG_AS_AP
- IFX.Version: 2
- ReqIF-WF.Type: Heading

###### ZZMA-FBDB-FIAH-CIEI_description: Description
The RDMA provides a unique master agent function identifier based access protection mechanism (APU) that protects the configuration of the RDMA registers.
The RDMA checks if the access master agent function identifier is enabled for the type of access (read access and write access, configured through the RDMA ACCEN registers) to the selected register.
Unauthorized access attempts are blocked by this mechanism.
- ReqIF-WF.Type: Information

###### ZZMA-FBDB-FIAH-CIEI_resetoperationalstate: Reset operational state
An application reset will set the configuration of this safety mechanism back to its default value.
- ReqIF-WF.Type: Information

###### ZZMA-FBDB-FIAH-CIEI_configurationandactivation: Configuration and activation
This safety mechanism is active after intentional configuration by application software through the ACCENx registers.
- ReqIF-WF.Type: Requirement

###### ZZMA-FBDB-FIAH-CIEI_test: Test
This safety measure can be tested after the RDMA ACCEN registers have been configured using an access to a protected register by a master agent function that is not enabled for the type of access configured by the RDMA ACCEN registers.
- ReqIF-WF.Type: Requirement

###### ZZMA-FBDB-FIAH-CIEI_reporting: Reporting
On detection of an access protection violation the RDMA will terminate the access with an FPI error that is detected by the BCU, see SM[HW]:FPI:ERROR_HANDLING.
- ReqIF-WF.Type: Information

###### ZZMA-FBDB-FIAH-CIEI_recommendederrorreaction: Recommended error reaction
System integrator to select an appropriate safe reaction in the SMU.
- ReqIF-WF.Type: Information

###### VSMA-FBDB-FIJH-ABHG: SM[HW]:RDMA:SV_AP
- IFX.Version: 1
- ReqIF-WF.Type: Heading

###### VSMA-FBDB-FIJH-ABHG_description: Description
Critical module registers are implemented with a write access restriction that allows access only to masters with supervisor (SV) mode privilege.
Unauthorized access attempts are blocked by this mechanism.
For a list of the registers protected by SV, see tables Register overview – access mode glossary and Register overview – RDMA (ascending offset address) in the User Manual.
- ReqIF-WF.Type: Information

###### VSMA-FBDB-FIJH-ABHG_resetoperationalstate: Reset operational state
The safety mechanism is active after application reset.
- ReqIF-WF.Type: Information

###### VSMA-FBDB-FIJH-ABHG_configurationandactivation: Configuration and activation
N.A.
- ReqIF-WF.Type: Requirement

###### VSMA-FBDB-FIJH-ABHG_test: Test
This safety measure can be tested by an write access to a protected register by a master agent function without supervisor (SV) access rights.
- ReqIF-WF.Type: Requirement

###### VSMA-FBDB-FIJH-ABHG_reporting: Reporting
On detection of an access protection violation the RDMA will terminate the access with an FPI error that is detected by the BCU, see SM[HW]:FPI:ERROR_HANDLING.
- ReqIF-WF.Type: Information

###### VSMA-FBDB-FIJH-ABHG_recommendederrorreaction: Recommended error reaction
System integrator to select an appropriate safe reaction in the SMU.
- ReqIF-WF.Type: Information

###### CKFA-FBDB-GDCD-HIAC: SM[HW]:RDMA:ENDINIT
- IFX.Version: 3
- ReqIF-WF.Type: Heading

###### CKFA-FBDB-GDCD-HIAC_description: Description
The RDMA provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – RDMA (ascending offset address) in the User Manual.
- ReqIF-WF.Type: Information

###### CKFA-FBDB-GDCD-HIAC_resetoperationalstate: Reset operational state
An application reset will set the configuration of this safety mechanism back to its default value.
- ReqIF-WF.Type: Information

###### CKFA-FBDB-GDCD-HIAC_configurationandactivation: Configuration and activation
This safety mechanism is active after intentional configuration by application software through the PROTE register.
- ReqIF-WF.Type: Requirement

###### CKFA-FBDB-GDCD-HIAC_test: Test
This safety measure can be tested after the PROT owner has been configured: Write access to a protected register by a master agent function that is not the PROT owner.
- ReqIF-WF.Type: Requirement

###### CKFA-FBDB-GDCD-HIAC_reporting: Reporting
On detection of an access protection violation the RDMA will terminate the access with FPI error that is detected by the BCU, see SM[HW]:FPI:ERROR_HANDLING.
- ReqIF-WF.Type: Information

###### CKFA-FBDB-GDCD-HIAC_recommendederrorreaction: Recommended error reaction
System integrator to select an appropriate safe reaction in the SMU.
- ReqIF-WF.Type: Information

###### OQHA-FBDB-GBGA-IGJC: SM[HW]:RDMA:SAFETY_ENDINIT
- IFX.Version: 2
- ReqIF-WF.Type: Heading

###### OQHA-FBDB-GBGA-IGJC_description: Description
The RDMA provides a PROT mechanisms (PROTSE) that protect the configuration of critical registers. The ACCEN mechanism is based on the master agent function identifier.
The PROT mechanism supports freedom from interference of different SW tasks. Unauthorized access attempts are blocked by these mechanisms.
For a list of the registers protected by PROTSE, see tables Register overview – access mode glossary and Register overview – RDMA (ascending offset address) in the User Manual.
- ReqIF-WF.Type: Information

###### OQHA-FBDB-GBGA-IGJC_resetoperationalstate: Reset operational state
An application reset will set the configuration of this safety mechanism back to its default value.
- ReqIF-WF.Type: Information

###### OQHA-FBDB-GBGA-IGJC_configurationandactivation: Configuration and activation
This safety mechanism is active after intentional configuration by application software through the PROTSE registers.
- ReqIF-WF.Type: Requirement

###### OQHA-FBDB-GBGA-IGJC_test: Test
This safety measure can be tested after the PROT owner has been configured using a write access to a protected register by a master agent function that is not the PROT owner.
- ReqIF-WF.Type: Requirement

###### OQHA-FBDB-GBGA-IGJC_reporting: Reporting
On detection of an access protection violation the RDMA will terminate the access with an FPI error that is detected by the BCU, see SM[HW]:FPI:ERROR_HANDLING.
- ReqIF-WF.Type: Information

###### OQHA-FBDB-GBGA-IGJC_recommendederrorreaction: Recommended error reaction
System integrator to select an appropriate safe reaction in the SMU.
- ReqIF-WF.Type: Information

##### MWRA-FJDE-ICDH-FFAF: Alarms
RDMA alarms
| Alarm Name | Safety Mechanism | Alarm flag to be cleared in |
| --- | --- | --- |
| RDMA SEP transaction integrity alarm | SM[HW]:RDMA:SEP_TRANSACTION_INTEGRITY | SMU only |
| RDMA redundancy mismatch alarm | SM[HW]:RDMA:REDUNDANCY | SMU only |
| RDMA configuration mismatch alarm | SM[HW]:RDMA:ACTIVE_CFG_CHECK SM[HW]:RDMA:ACTIVE_CFG_CHECK_SCC | SMU only |
| RCB bus error event alarm | SM[HW]:RDMA:SV_AP SM[HW]:RDMA:CFG_AS_AP SM[HW]:RDMA:ENDINIT SM[HW]:RDMA:SAFETY_ENDINIT | SMU only |
- IFX.Version: 1
- ReqIF-WF.Type: Information

##### XHJA-FAFF-HGIC-FAHD: External safety mechanisms
- IFX.Version: 1
- ReqIF-WF.Type: Information

###### EUHA-FBDH-HCBH-EJJB: ESM[SW]:RDMA:ISR_MONITOR
This ESM shall detect missing or unintended interrupts originating from the RDMA module. Usage of interrupts in this FB depends on the use cases and code implementation.
- Channel completion or batch completion interrupts: When an RDMA channel completes the configured operation or completes the extraction of the specified batch of targets, it generates an interrupt to the interrupt router if configured to do so. The target interrupt service provider is usually a processor capable of running software in an interrupt service routine.
- Missing interrupts: If an interrupt generated by the RDMA channel does not reach the intended target, the application software does not get notified of the completed operation. The application software shall detect such a missing interrupt by implementing a checking mechanism such as a timeout
- Unintended interrupts: If the RDMA generates an unintended interrupt, the application software is notified too early of a channel completion or the completion of a batch of target extraction. The interrupt service routine implemented by the application software shall detect an unintended interrupt by reading the number of completed operations in the RDMA CHc_CTRL_TRIGSTAT register and comparing them against the expected number of operations
- Error interrupt: When the RDMA encounters an error condition, the RDMA generates an error interrupt to the interrupt router if configured to do so. The target interrupt service provider is usually a processor capable of running software in an interrupt service routine.
- Missing interrupts: If an error interrupt generated by the RDMA channel does not reach the intended target, the application software does not get notified of the error condition. The application software shall detect such a missing interrupt by executing a periodic check of the RDMA error status register ERRSR for pending error conditions at least once within every fault-tolerant time interval
- Unintended interrupts: If the RDMA generates an unintended error interrupt, the interrupt service routine implemented by the application software will not find any error flags set when it reads the RDMA error status register ERRSR. The application software shall trigger an appropriate reaction
- IFX.Version: 1
- ReqIF-WF.Type: Heading

###### EUHA-FBDH-HCBH-EJJB_description: Description
- ReqIF-WF.Type: Requirement

###### EUHA-FBDH-HCBH-EJJB_test: Test
- Channel completion or batch completion interrupt
- Missing interrupts: Application software can prevent the RDMA from generating an RDMA channel completion or batch completion interrupt by writing bit-field CHc_CTRL_CHCSR.IENC to 0 B
- Unintended interrupts: Application software can trigger an RDMA channel completion or batch completion interrupt by writing bit-field CHc_CTRL_CHCSR.SIT to 1 B
- Error interrupt
- Missing interrupts: Application software can prevent the RDMA from generating an error interrupt by clearing bit-fields EER.ESER, EER.EDER and CHc_CTRL_TSR.ETRL
- Unintended interrupts: Application software can trigger an RDMA error interrupt by writing bit-field ERRINTR.SIT to 1 B
- ReqIF-WF.Type: Requirement

#### YQVA-FJAC-JGEA-CJBG: Radar interface (RIF)
The RIF connects a fast external automotive RF transceiver with up to four channels with an SPU (Signal Processing Unit), and to the system memory through the SRI. RIF receives data either in the LVDS mode or over the CSI-2 interface. Both of these modes share the same input pads.
Six pairs of input pads are available to support six differential signals with four data signals, a clock signal, and a frame signal.
Each multi-channel external ADC is connected over LVDS pads conforming to IEEE 1596.3 General Purpose Link standard or a CSI-2 interface over the D-PHY physical layer. The CSI-2 interface conforms to MIPI specification V1.2 and the D-PHY conforms to MIPI specification V1.2
LVDS mode consists of a group of four data signals which share one clock and one frame signal. In the CSI-2 mode, a group of four data signals share one clock signal.
RIF consists of two internal processing pipelines namely radar processing pipeline and internal bypass pipeline. The radar processing pipeline consists of FRU to construct ADC samples, quad FIFO and lane management block, and the data memory interface to write to the SPU or the bypass unit to be written to the system memory. The bypass pipeline is only used in the CSI-2 mode and routes the raw IDI data to the bypass unit to be written to the system memory.
RIF overview
- IFX.Version: 1
- ReqIF-WF.Type: Information

##### XHNA-FAFF-HHFJ-BEDF: Internal safety mechanisms
- IFX.Version: 1
- ReqIF-WF.Type: Information

###### MJXA-FBDD-DEED-BJAB: SM[HW]:RIF:ACTIVE_CFG_CHECK
- IFX.Version: 28
- ReqIF-WF.Type: Heading

###### MJXA-FBDD-DEED-BJAB_description: Description
The RIF configuration checksum is a cyclic redundancy checksum (CRC) calculated from data stored in the RIF configuration registers. The RIF periodically parses the RIF configuration registers to calculate a RIF configuration checksum and compares it with an expected CRC to detect any missing or corrupted configuration data.
The register CRC, once enabled, runs periodically in a round robin fashion by taking the value of a register and writing it to the RIF’s CRC engine each 64 fADAS clock cycles. After the CRC value has been computed for the complete register set, it is compared with the value stored in the REGCRC.CRC bit-field. If comparison fails, then an alarm is raised.
- ReqIF-WF.Type: Information

###### MJXA-FBDD-DEED-BJAB_resetoperationalstate: Reset operational state
The safety mechanism is disabled after application reset.
- ReqIF-WF.Type: Information

###### MJXA-FBDD-DEED-BJAB_configurationandactivation: Configuration and activation
After writing the initial RIF configuration, the application software shall compute the expected CRC of the configuration data and store it in the REGCRC register using the CRC-32 polynomial as specified in the IEEE 802.3 standard, which is supported by the TriCore™ CRC-32 instruction. Afterwards, the application software shall activate this safety mechanism by setting SFCON.REGCRCEN = 10 B.
When updating the RIF configuration, the application software shall deactivate this safety mechanism (configure SFCON.REGCRCEN = 10 B), update the configuration of the RIF, write new CRC value in the REGCRC register and enable the register CRC engine again (configure SFCON.REGCRCEN = 10 B), which restarts it from the initial state.
For the configuration data CRC computation, the application software shall calculate the accumulated CRC value of the following registers: ESI, FLM, DMI, RSM0, RSM1, RSM2, RSM3, INTCON, FLAGSSET, FLAGSCL, INTEN, INTFLG, INTFLGS, INTFLGC, FWDG, DFU, RSM2CAP, LVDSCON, SMSTAT, DBG0, DBG1, SFCON, FRM, CSIVCEN, BMU, BUCFG, LVDBYPAD, LVDMODTH, VCFGi_CSIBYPAD, VCFGi_CSIMODTH, IDIPRTY, CSIFDG, DPHYCFG, DPHYTX, DPHY0ADD, DPHY1ADD, DPHY2ADD, DPHY3ADD, DPHY4ADD, DPHYBIST, DPHY0PLL, DPHY1PLL, DPHY2PLL, DPHY3PLL, DPHYSB, DPHY0LDO, DPHY1LDO, DPHY2LDO, where the LSB of each register is the first bit in the data stream (supported by the TriCore™ CRC-32 instruction). Please note that the configuration data values shall be taken from the application software (stored for example in RAM), not by reading the register contents.
For the CRC calculation the application software shall only consider the "rw“ fields listed above while their volatile "rh“ and write only "w“ fields shall be replaced by zeros.
For the CRC calculation, the application software shall assume the following value for the register SFCON.REGCRCEN = 10 B (enabled)."
- ReqIF-WF.Type: Requirement

###### MJXA-FBDD-DEED-BJAB_test: Test
The hardware logic of this safety mechanism is tested by SM[HW]:RIF:ACTIVE_CFG_CHECK_SCC. The application software shall test the alarm path of this safety mechanism at least once per Multi-Point Fault Detection Time Interval (MPFDTI) by writing an invalid value to REGCRC.CRC while SM[HW]:RIF:ACTIVE_CFG_CHECK is enabled.
- ReqIF-WF.Type: Requirement

###### MJXA-FBDD-DEED-BJAB_reporting: Reporting
Upon detection of a mismatch between the computed and expected CRC values, an alarm is sent to the SMU.
- ReqIF-WF.Type: Information

###### MJXA-FBDD-DEED-BJAB_recommendederrorreaction: Recommended error reaction
System integrator to select an appropriate safe reaction in the SMU.
- ReqIF-WF.Type: Information

###### LWOA-FBDB-HADB-AHDB: SM[HW]:RIF:CONTROL_REDUNDANCY
Description
The [RIF] duplicates the state machine, the data path and the bypass unit. The [RIF] continuously monitors the outputs of the duplicated logic. If the [RIF] detects an output mismatch, the [RIF] triggers an alarm.
The [RIF] module provides an optional safety feature providing increased data path integrity. The safety mechanism consists of:
- A monitor function covering the DFU and the bypass unit which works by implementing a duplicate copy of the monitored logic with the same inputs as the functional copy and a set of comparators which compares the outputs from the functional and monitor copies of the logic
- The safety feature is disabled by default, and can be enabled by software by using the bit-field SFCON.LRNDE. If the logic redundancy comparator detects mismatch, an [SMU] alarm is triggered
Reset operational state
The safety mechanism is disabled after[Application Reset].
Configuration and activation
The [Application SW] shall enable the internal [RIF] logic redundancy (configure SFCON.LRNDE = 10B).
Test
The logic redundancy compare function provides the application software with the ability to generate an alarm by setting the redundantly encoded SFCON.LRNDCT = ON. This will inject an error into the comparators until it is set to OFF.
The following faults will be detected:
- A stuck at fault on the alarm signal path
Reporting
On detection of logic redundancy error, an alarm is sent to the [SMU].
Recommended error reaction
System integrator to select appropriate safe reaction in [SMU].
- IFX.Version: 1
- ReqIF-WF.Type: Heading

###### EFMA-FBDD-DGJC-HDHD: SM[HW]:RIF:ERROR_HANDLING
- IFX.Version: 1
- ReqIF-WF.Type: Heading

###### EFMA-FBDD-DGJC-HDHD_description: Description
The [MMIC] data checksum is a cyclic redundancy checksum calculated and appended to data transmitted from the [MMIC] to the [RIF]. The calculation of the [MMIC] data checksum fulfils the IEEE 802.3 standard. If the [MMIC] transmits radar data to the [RIF], the [MMIC] shall append the radar data with a [MMIC] data checksum. As long as the [MMIC] is transmitting radar data to the [RIF], the [RIF] shall calculate a [MMIC] data checksum for the received radar data. As soon as the [RIF] receives the appended [MMIC] data checksum, the [RIF] compares the calculated [MMIC] data checksum to the appended [MMIC] data checksum. If the [RIF] does not match the calculated and appended [MMIC] data checksums, the [RIF] triggers an interrupt.
- ReqIF-WF.Type: Information

###### EFMA-FBDD-DGJC-HDHD_resetoperationalstate: Reset operational state
The safety mechanism is disabled after [Application Reset].
- ReqIF-WF.Type: Information

###### EFMA-FBDD-DGJC-HDHD_configurationandactivation: Configuration and activation
The [Application SW] shall enable the [RIF] to perform a [CRC] integrity check of radar data (configure FLM.CRCEN = 1B).
The [Application SW] shall enable the [CRC] error interrupt service requests (for n = 0-3, configure INTCON.CRCEn = 1B).
- ReqIF-WF.Type: Requirement

###### EFMA-FBDD-DGJC-HDHD_test: Test
ESM[SW]:RIF:ERROR_HANDLING
- ReqIF-WF.Type: Requirement

###### EFMA-FBDD-DGJC-HDHD_reporting: Reporting
On detection of [CRC] error, an interrupt service request is raised.
- ReqIF-WF.Type: Information

###### EFMA-FBDD-DGJC-HDHD_recommendederrorreaction: Recommended error reaction
System integrator to select appropriate safe reaction in [SMU].
- ReqIF-WF.Type: Information

###### REMA-FBDD-EAAB-BDHH: SM[HW]:RIF:TEMPORAL_MONITOR
- IFX.Version: 1
- ReqIF-WF.Type: Heading

###### REMA-FBDD-EAAB-BDHH_description: Description
In the [LVDS] mode, the [RIF] detects missing data by running a frame watchdog timer and a sample counter. Frame Watchdog is one 10-bit free running timer monitoring the frame signal and being reset by the incoming frames. It is driven by the RIF kernel frequency fADAS. It is configured to count for longer than the maximal serial frame length that appears in an application ([CRC] frame length if [CRC] is used, otherwise data frame length). If there is a pause in the data stream, the watchdog timer reaches the threshold. This is interpreted as an end of a ramp. At the end of each ramp, [RIF] compares the received number of samples with the configured number of samples to detect the event of missing data.
- ReqIF-WF.Type: Information

###### REMA-FBDD-EAAB-BDHH_resetoperationalstate: Reset operational state
After reset, the default value of the register FWDG.THRESHOLD is 0. With this setting, the frame watchdog does not generate ramp end interrupts and the safety mechanism is disabled.
- ReqIF-WF.Type: Information

###### REMA-FBDD-EAAB-BDHH_configurationandactivation: Configuration and activation
The [Application SW] shall enable the frame watchdog (configure FWDG.THRESHOLD to an appropriate value).
The [Application SW] shall configure the expected number of samples per ramp (RSM2.SAMPLES)
- ReqIF-WF.Type: Requirement

###### REMA-FBDD-EAAB-BDHH_test: Test
This safety measure can be tested by writing an invalid value to RSM2.SAMPLES while frame watchdog timer is enabled.
- ReqIF-WF.Type: Requirement

###### REMA-FBDD-EAAB-BDHH_reporting: Reporting
On detecting missing data, an interrupt service request is raised.
- ReqIF-WF.Type: Information

###### REMA-FBDD-EAAB-BDHH_recommendederrorreaction: Recommended error reaction
System integrator to select appropriate safe reaction in [SMU].
- ReqIF-WF.Type: Information

###### YTCA-FDHD-FFBI-HCGF: SM[HW]:RIF:CFG_AS_AP
- IFX.Version: 1
- ReqIF-WF.Type: Heading

###### YTCA-FDHD-FFBI-HCGF_description: Description
The [RIF] provides a unique master agent function identifier-based access protection mechanism (APU) that protects the configuration of the RIF registers.
The RIF checks if the access master agent function identifier is enabled for the type of access (read access and write access, configured through the [RIF] ACCEN registers) to the selected register.
Unauthorized access attempts are blocked by this mechanism.
- ReqIF-WF.Type: Information

###### YTCA-FDHD-FFBI-HCGF_resetoperationalstate: Reset operational state
An application reset will set the configuration of this safety mechanism back to its default value.
- ReqIF-WF.Type: Information

###### YTCA-FDHD-FFBI-HCGF_configurationandactivation: Configuration and activation
This safety mechanism is active after intentional configuration by application software through the ACCENx registers.
- ReqIF-WF.Type: Requirement

###### YTCA-FDHD-FFBI-HCGF_test: Test
This safety measure can be tested after the RIF ACCEN registers have been configured using an access to a protected register by a master agent function that is not enabled for the type of access.
- ReqIF-WF.Type: Requirement

###### YTCA-FDHD-FFBI-HCGF_reporting: Reporting
On detection of an access protection violation the [RIF] will terminate the access with an FPI error that is detected by the BCU, see SM[HW]:FPI:ERROR_HANDLING.
- ReqIF-WF.Type: Information

###### YTCA-FDHD-FFBI-HCGF_recommendederrorreaction: Recommended error reaction
System integrator to select appropriate safe reaction in [SMU].
- ReqIF-WF.Type: Information

###### IFMA-FDHD-FHFJ-GBHA: SM[HW]:RIF:SV_AP
- IFX.Version: 8
- ReqIF-WF.Type: Heading

###### IFMA-FDHD-FHFJ-GBHA_description: Description
Critical module registers are implemented with a write access restriction that allows access only to masters with supervisor (SV) mode privilege.
Unauthorized access attempts are blocked by this mechanism.
For a list of the registers protected by SV, see tables Register overview – access mode glossary and Register overview – RIF (ascending offset address) in the User Manual.
- ReqIF-WF.Type: Information

###### IFMA-FDHD-FHFJ-GBHA_resetoperationalstate: Reset operational state
The safety mechanism is active after application reset.
- ReqIF-WF.Type: Information

###### IFMA-FDHD-FHFJ-GBHA_configurationandactivation: Configuration and activation
Not applicable
- ReqIF-WF.Type: Requirement

###### IFMA-FDHD-FHFJ-GBHA_test: Test
This safety measure can be tested by an write access to a protected register by a master agent function without supervisor (SV) access rights.
- ReqIF-WF.Type: Requirement

###### IFMA-FDHD-FHFJ-GBHA_reporting: Reporting
On detection of an access protection violation the RIF will terminate the access with an FPI error that is detected by the BCU, see SM[HW]:FPI:ERROR_HANDLING.
- ReqIF-WF.Type: Information

###### IFMA-FDHD-FHFJ-GBHA_recommendederrorreaction: Recommended error reaction
System integrator to select appropriate safe reaction in SMU.
- ReqIF-WF.Type: Information

###### SLCA-FDHD-FIGB-GEFJ: SM[HW]:RIF:ENDINIT
- IFX.Version: 1
- ReqIF-WF.Type: Heading

###### SLCA-FDHD-FIGB-GEFJ_description: Description
The [RIF] provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – RIF (ascending offset address) in the User Manual.
- ReqIF-WF.Type: Information

###### SLCA-FDHD-FIGB-GEFJ_resetoperationalstate: Reset operational state
An application reset will set the configuration of this safety mechanism back to its default value.
- ReqIF-WF.Type: Information

###### SLCA-FDHD-FIGB-GEFJ_configurationandactivation: Configuration and activation
This safety mechanism is active after intentional configuration by application software through the PROTE register.
- ReqIF-WF.Type: Requirement

###### SLCA-FDHD-FIGB-GEFJ_test: Test
This safety measure can be tested after the PROT owner has been configured: Write access to a protected register by a master agent function that is not the PROT owner.
- ReqIF-WF.Type: Requirement

###### SLCA-FDHD-FIGB-GEFJ_reporting: Reporting
On detection of an access protection violation the [RIF] will terminate the access with an FPI error that is detected by the BCU, see SM[HW]:FPI:ERROR_HANDLING.
- ReqIF-WF.Type: Information

###### SLCA-FDHD-FIGB-GEFJ_recommendederrorreaction: Recommended error reaction
System integrator to select appropriate safe reaction in [SMU].
- ReqIF-WF.Type: Information

###### ITAA-FDHD-GFFD-HJIF: SM[HW]:RIF:SAFETY_ENDINIT
- IFX.Version: 7
- ReqIF-WF.Type: Heading

###### ITAA-FDHD-GFFD-HJIF_description: Description
The RIF provides a PROT mechanism (PROTSE) that protect the configuration of critical registers. The ACCEN mechanism is based on the master agent function identifier.
The PROT mechanism supports freedom from interference of different software tasks. Unauthorized access attempts are blocked by these mechanisms.
For a list of the registers protected by PROTSE, see tables Register overview – Access mode glossary and Register overview – RIF(ascending offset address) in the User Manual.
- ReqIF-WF.Type: Information

###### ITAA-FDHD-GFFD-HJIF_resetoperationalstate: Reset operational state
An application reset will set the configuration of this safety mechanism back to its default value.
- ReqIF-WF.Type: Information

###### ITAA-FDHD-GFFD-HJIF_configurationandactivation: Configuration and activation
This safety mechanism is active after intentional configuration by application software through the PROTSE registers.
- ReqIF-WF.Type: Requirement

###### ITAA-FDHD-GFFD-HJIF_test: Test
This safety measure can be tested after the PROT owner has been configured: Write access to a protected register by a master agent function that is not the PROT owner.
- ReqIF-WF.Type: Requirement

###### ITAA-FDHD-GFFD-HJIF_reporting: Reporting
On detection of an access protection violation the RIF will terminate the access with an FPI error that is detected by the BCU, see SM[HW]:FPI:ERROR_HANDLING.
- ReqIF-WF.Type: Information

###### ITAA-FDHD-GFFD-HJIF_recommendederrorreaction: Recommended error reaction
System integrator to select appropriate safe reaction in SMU.
- ReqIF-WF.Type: Information

###### VPXA-FDHD-HCIG-JFFC: SM[HW]:RIF:SM_CHECK
- IFX.Version: 1
- ReqIF-WF.Type: Heading

###### VPXA-FDHD-HCIG-JFFC_description: Description
The [RIF] provides a safety mechanism to monitor the integrity of other [RIF] safety mechanisms. The safety mechanism operates by maintaining a duplicate copy of all the monitored logic ("active" logic). The duplicate copy has the logic states of the registers inverted. The outputs of the "active" logic and the duplicate copy are compared with a hardware comparator.
An alarm is always generated if the "active" copy of the logic detects an error. This safety mechanism will not modify that behaviour. The status bit in INTCON is set if the state of the duplicate logic differs from the state of the "active" logic. The expanded truth table is as follows:
1. there is an error and both hardware monitoring have the same result:
1. RIF [SMU] Alarm
2. bit is not set in INTCON.SMCF
2. there is an error but both hardware monitoring have a different result:
1. RIF [SMU] Alarm
2. bit set in INTCON.SMCF
3. there is no error and both hardware monitoring have same result:
1. no Alarm
2. bit is not set in INTCON.SMCF
4. there is no error but both hardware monitoring have a different result:
1. no Alarm
2. bit set in INTCON.SMCF
This safety mechanism is used to monitor the following RIF safety mechanisms:
- SM[HW]:RIF:CONTROL_REDUNDANCY
- SM[HW]:RIF:ACTIVE_CFG_CHECK
- ReqIF-WF.Type: Information

###### VPXA-FDHD-HCIG-JFFC_resetoperationalstate: Reset operational state
This safety mechanism is enabled after application reset.
- ReqIF-WF.Type: Information

###### VPXA-FDHD-HCIG-JFFC_configurationandactivation: Configuration and activation
N.A.
- ReqIF-WF.Type: Requirement

###### VPXA-FDHD-HCIG-JFFC_test: Test
This safety measure can be tested by writing invalid configurations to the enable bits of the safety mechanisms which are covered by this safety mechanism.
- ReqIF-WF.Type: Requirement

###### VPXA-FDHD-HCIG-JFFC_reporting: Reporting
Upon detecting a failure in the safety mechanisms, INTCON.SMCF bit is set as explained above.
- ReqIF-WF.Type: Information

###### VPXA-FDHD-HCIG-JFFC_recommendederrorreaction: Recommended error reaction
System integrator to select appropriate safe reaction in [SMU].
- ReqIF-WF.Type: Information

###### DPXA-FDHF-DGEC-GIJC: SM[HW]:RIF:ACTIVE_CFG_CHECK_SCC
- IFX.Version: 11
- ReqIF-WF.Type: Heading

###### DPXA-FDHF-DGEC-GIJC_description: Description
The active configuration check has to sequence through states to read each configuration register and then compare the resulting CRC over the registers with the expected value. This sequential logic is duplicated and the signal that triggers the comparison of CRC values is checked against the duplicate. A fault is detected when the values of the signal and its duplicate differ.
- ReqIF-WF.Type: Information

###### DPXA-FDHF-DGEC-GIJC_resetoperationalstate: Reset operational state
This safety mechanism is active after application reset.
- ReqIF-WF.Type: Information

###### DPXA-FDHF-DGEC-GIJC_configurationandactivation: Configuration and activation
Not applicable
- ReqIF-WF.Type: Requirement

###### DPXA-FDHF-DGEC-GIJC_test: Test
Not applicable
- ReqIF-WF.Type: Requirement

###### DPXA-FDHF-DGEC-GIJC_reporting: Reporting
Upon detecting a fault, an interrupt service request is raised and SMSTAT.SMCF bit is set.
- ReqIF-WF.Type: Information

###### DPXA-FDHF-DGEC-GIJC_recommendederrorreaction: Recommended error reaction
The application software shall trigger an appropriate safe reaction in the interrupt handler.
- ReqIF-WF.Type: Information

###### ZDJA-FDIJ-HCDD-FIGI: SM[HW]RIF.CONTROL_REDUNDANCY_SCC
Description
A continuously running hardware-based test injects a fault at every input of the comparator in a sequential manner. A special unit detects that the fault has been propagated to the correct comparator node. If such is not the case either the comparator has a defect or a real fault took place and a lockstep alarm is generated.
Reset operational state
The safety mechanism is enabled after [Application Reset].
Configuration and activation
N.A.
Test
It is a self checking safety mechanism.
Reporting
Upon detecting a fault, an alarm is sent to the [SMU].
Recommended error reaction
System integrator to select appropriate safe reaction in [SMU].
- IFX.Version: 1
- ReqIF-WF.Type: Information

###### OKLA-FDIB-CACC-FAJE: SM[HW]:RIF:PARITY_CHECK
- IFX.Version: 13
- ReqIF-WF.Type: Heading

###### OKLA-FDIB-CACC-FAJE_description: Description
The RIF module provides an optional safety feature providing increased data path integrity in its internal bypass path. The safety mechanism consists of a parity check between the FRU and the bypass unit.
- ReqIF-WF.Type: Information

###### OKLA-FDIB-CACC-FAJE_resetoperationalstate: Reset operational state
The safety mechanism is disabled after application reset.
- ReqIF-WF.Type: Information

###### OKLA-FDIB-CACC-FAJE_configurationandactivation: Configuration and activation
The application software shall enable the RIF internal bypass path parity check (configure SFCON.PRTYEN = 10 B).
- ReqIF-WF.Type: Requirement

###### OKLA-FDIB-CACC-FAJE_test: Test
The parity check function provides the application software with the ability to generate an alarm by setting the redundantly encoded SFCON.PRTYTST = ON. This will inject an error into the parity check logic until it is set to OFF.
The following faults will be detected:
- A stuck at fault on the alarm signal path
The application software shall test the alarm path of this safety mechanism at least once per MPFDTI.
- ReqIF-WF.Type: Requirement

###### OKLA-FDIB-CACC-FAJE_reporting: Reporting
On detection of parity check error,an alarm is sent to the SMU.
- ReqIF-WF.Type: Information

###### OKLA-FDIB-CACC-FAJE_recommendederrorreaction: Recommended error reaction
System integrator to select appropriate safe reaction in SMU.
- ReqIF-WF.Type: Information

##### AXEA-EIIF-CFFF-FAJH: Alarms
RIF alarms
| Alarm name | Safety mechanism | Alarm flag to be cleared in |
| --- | --- | --- |
| RIF error alarm | SM[HW]:RIF:ACTIVE_CFG_CHECK SM[HW]:RIF:CONTROL_REDUNDANCY SM[HW]RIF.CONTROL_REDUNDANCY_SCC SM[HW]RIF.PARITY_CHECK | SMU only |
- IFX.Version: 1
- ReqIF-WF.Type: Information

##### WLMA-FAFF-HHFJ-GFIG: External safety mechanisms
- IFX.Version: 1
- ReqIF-WF.Type: Information

###### VCNA-FBDF-AJDG-DGCB: ESM[SW]:RIF:ERROR_HANDLING
- IFX.Version: 1
- ReqIF-WF.Type: Heading

###### VCNA-FBDF-AJDG-DGCB_description: Description
The [MMIC] can optionally append a 32-bit [CRC] word at the end of radar data from each ramp. [RIF] calculates the [CRC] over the received data and compares it with the 32-bit [CRC] word to detect incorrect or missing Rx data.
- ReqIF-WF.Type: Requirement

###### VCNA-FBDF-AJDG-DGCB_resetoperationalstate: Reset operational state
Not applicable
- ReqIF-WF.Type: Information

###### VCNA-FBDF-AJDG-DGCB_configurationandactivation: Configuration and activation
The [Application SW] shall enable the [RIF] [CRC] check (configure FLM.CRCEN = 1B).
- ReqIF-WF.Type: Requirement

###### VCNA-FBDF-AJDG-DGCB_test: Test
This test can be implemented by appending an incorrect [CRC] word and the [RIF] is expected to raise an interrupt service request.
- ReqIF-WF.Type: Requirement

###### VCNA-FBDF-AJDG-DGCB_recommendederrorreaction: Recommended error reaction
System integrator to select appropriate safe reaction in [SMU].
- ReqIF-WF.Type: Information

###### UNPA-FBDF-CEHH-GHEA: ESM[SW]:RIF:ISR_MONITOR
- IFX.Version: 1
- ReqIF-WF.Type: Heading

###### UNPA-FBDF-CEHH-GHEA_description: Description
This ESM shall detect missing or unintended interrupts originating from the RIF module.
- Attention interrupts: When the RIF completes processing certain tasks or identifies certain events, it generates interrupts to the interrupt router if configured to do so. The target interrupt service provider is usually a processor capable of running software in an interrupt service routine
- Missing interrupts: If an interrupt generated by the RIF does not reach the intended target, the application software does not get notified of the completed operation. The application software shall detect such a missing interrupt by implementing a checking mechanism such as a timeout
- Unintended interrupts: If the RIF generates an unintended interrupt, the application software is notified too early or spuriously of an event in the RIF. The interrupt service routine implemented by the application software shall detect an unintended interrupt by reading the RIF interrupt registers (INTCON, INTEN, INTFLG) registers, depending on the source of the interrupt and checking that the interrupt status is consistent with the masked interrupt sources
- Error interrupts: When the RIF encounters an error condition, the RIF generates an error interrupt to the interrupt router if configured to do so. The target interrupt service provider is usually a processor capable of running software in an interrupt service routine
- Missing interrupts: If an error interrupt generated by the RIF does not reach the intended target, the application software does not get notified of the error condition. The application software shall detect such a missing interrupt by executing a periodic check of the RIF error status registers (INTCON and INTFLG) for pending error conditions at least once within every fault-tolerant time interval
- Unintended interrupts: If the RIF generates an unintended error interrupt, the interrupt service routine implemented by the application software will not find any error flags set when it reads the RIF error status registers (INTCON, INTEN, INTFLG). The application software shall trigger an appropriate reaction
- ReqIF-WF.Type: Requirement

###### UNPA-FBDF-CEHH-GHEA_resetoperationalstate: Reset operational state
Not applicable
- ReqIF-WF.Type: Information

###### UNPA-FBDF-CEHH-GHEA_configurationandactivation: Configuration and activation
Not applicable
- ReqIF-WF.Type: Requirement

###### UNPA-FBDF-CEHH-GHEA_test: Test
- Missing interrupts: [Application software] can prevent the RIF from generating a given attention interrupt by setting RIF interrupt control registers (INTCON and INTEN)
- Unintended interrupts: Application software can trigger a given RIF attention interrupt using (FLAGSSET and INTFLGS)
- ReqIF-WF.Type: Requirement

###### UNPA-FBDF-CEHH-GHEA_recommendederrorreaction: Recommended error reaction
System integrator to select appropriate safe reaction in [SMU].
- ReqIF-WF.Type: Information

###### HIBA-FBGD-IEED-CDAB: ESM[SW]:RIF:CSI-2_ERROR_HANDLING
- IFX.Version: 1
- ReqIF-WF.Type: Heading

###### HIBA-FBGD-IEED-CDAB_description: Description
CSI-2 host controller monitors the integrity of the data and triggers an interrupt if an error is detected.
- ReqIF-WF.Type: Requirement

###### HIBA-FBGD-IEED-CDAB_resetoperationalstate: Reset operational state
Not applicable
- ReqIF-WF.Type: Information

###### HIBA-FBGD-IEED-CDAB_configurationandactivation: Configuration and activation
Not applicable
- ReqIF-WF.Type: Requirement

###### HIBA-FBGD-IEED-CDAB_test: Test
Application software can trigger a given CSI-2 interrupt by writing to INT_FORCE<group> registers.
- ReqIF-WF.Type: Requirement

###### HIBA-FBGD-IEED-CDAB_recommendederrorreaction: Recommended error reaction
System integrator to select appropriate safe reaction in [SMU].
- ReqIF-WF.Type: Information

###### WOZA-FDHE-EBJC-JCJD: ESM[SW]:RIF:SM_CHECK
- IFX.Version: 1
- ReqIF-WF.Type: Heading

###### WOZA-FDHE-EBJC-JCJD_description: Description
The [Application SW] shall monitor the status of the safety mechanism SM[HW]:RIF:SM_CHECK by polling the Safety Mechanism Control Status and take appropriate measures.
- ReqIF-WF.Type: Requirement

###### WOZA-FDHE-EBJC-JCJD_resetoperationalstate: Reset operational state
Not applicable
- ReqIF-WF.Type: Information

###### WOZA-FDHE-EBJC-JCJD_configurationandactivation: Configuration and activation
Not applicable
- ReqIF-WF.Type: Requirement

###### WOZA-FDHE-EBJC-JCJD_test: Test
This test can be implemented by regularly polling the safety mechanism control status (INTCON.SMCF = 1B)
- ReqIF-WF.Type: Requirement

###### WOZA-FDHE-EBJC-JCJD_recommendederrorreaction: Recommended error reaction
System integrator to select appropriate safe reaction in [SMU].
- ReqIF-WF.Type: Information

#### GIXA-EIIF-CEHE-DCDJ: Radar Memory (RMEM)
- IFX.Version: 1
- ReqIF-WF.Type: Information

##### OSIA-FAFF-HHHG-FAFF: Internal safety mechanisms
- IFX.Version: 1
- ReqIF-WF.Type: Information

###### PESA-FBEJ-DAAF-GDDF: SM[HW]:RMEM:CFG_AS_AP
- IFX.Version: 1
- ReqIF-WF.Type: Heading

###### PESA-FBEJ-DAAF-GDDF_description: Description
The RMEM provides a unique master agent function identifier based access protection mechanism (APU) that protects the configuration of the RMEM registers.
The RMEM checks if the access master agent function identifier is enabled for the type of access (read access and write access, configured through the RMEM ACCEN registers) to the selected resource.
Unauthorized access attempts are blocked by this mechanism.
- ReqIF-WF.Type: Information

###### PESA-FBEJ-DAAF-GDDF_resetoperationalstate: Reset operational state
An application reset will set the configuration of this safety mechanism back to its default value.
- ReqIF-WF.Type: Information

###### PESA-FBEJ-DAAF-GDDF_configurationandactivation: Configuration and activation
This safety mechanism is active after intentional configuration by application software through the ACCENx registers.
- ReqIF-WF.Type: Requirement

###### PESA-FBEJ-DAAF-GDDF_test: Test
This safety measure can be tested after the RMEM ACCEN registers have been configured using an access to a protected register by a master agent function that is not enabled for the type of access configured by the RDMA ACCEN registers.
- ReqIF-WF.Type: Requirement

###### PESA-FBEJ-DAAF-GDDF_reporting: Reporting
On detection of an access protection violation the RMEM will terminate the access with an SRI error that is detected by the XBAR, see SM[HW]:SRI:ERROR_HANDLING.
- ReqIF-WF.Type: Information

###### PESA-FBEJ-DAAF-GDDF_recommendederrorreaction: Recommended error reaction
System integrator to select an appropriate safe reaction in the SMU.
- ReqIF-WF.Type: Information

###### SKMA-FBEJ-DABH-FGBB: SM[HW]:RMEM:SV_AP
- IFX.Version: 1
- ReqIF-WF.Type: Heading

###### SKMA-FBEJ-DABH-FGBB_description: Description
Critical module registers are implemented with a write access restriction that allows access only to masters with supervisor (SV) mode privilege.
Unauthorized access attempts are blocked by this mechanism.
For a list of the registers protected by SV, see tables Register overview – access mode glossary and Register overview – RMEM (ascending offset address) in the User Manual.
- ReqIF-WF.Type: Information

###### SKMA-FBEJ-DABH-FGBB_resetoperationalstate: Reset operational state
The safety mechanism is active after application reset.
- ReqIF-WF.Type: Information

###### SKMA-FBEJ-DABH-FGBB_configurationandactivation: Configuration and activation
N.A.
- ReqIF-WF.Type: Requirement

###### SKMA-FBEJ-DABH-FGBB_test: Test
This safety measure can be tested by an write access to a protected register by a master agent function without supervisor (SV) access rights.
- ReqIF-WF.Type: Requirement

###### SKMA-FBEJ-DABH-FGBB_reporting: Reporting
On detection of an access protection violation the RMEM will terminate the access with an SRI error that is detected by the XBAR, see SM[HW]:SRI:ERROR_HANDLING.
- ReqIF-WF.Type: Information

###### SKMA-FBEJ-DABH-FGBB_recommendederrorreaction: Recommended error reaction
System integrator to select an appropriate safe reaction in the SMU.
- ReqIF-WF.Type: Information

###### KQQA-FBEJ-DACC-DIGI: SM[HW]:RMEM:SAFETY_ENDINIT
- IFX.Version: 1
- ReqIF-WF.Type: Heading

###### KQQA-FBEJ-DACC-DIGI_description: Description
The RMEM provides a PROT mechanisms (PROTSE) that protect the MEMCON and SCTRL registers.
The RMEM also provides a PROT mechanism (PROTRGN) that protects the configuration of the access protection mechanism (ACCEN). The ACCEN mechanism is based on the master agent function identifier. This supports freedom from interference of different SW tasks. Unauthorized access attempts are blocked by this mechanism.
For a list of the registers protected by PROTSE and PROTRGN, see tables Register overview – access mode glossary and Register overview – RMEM (ascending offset address) in the User Manual.
- ReqIF-WF.Type: Information

###### KQQA-FBEJ-DACC-DIGI_resetoperationalstate: Reset operational state
An application reset will set the configuration of this safety mechanism back to its default value.
- ReqIF-WF.Type: Information

###### KQQA-FBEJ-DACC-DIGI_configurationandactivation: Configuration and activation
This safety mechanism is active after intentional configuration by application software through the PROTSE and PROTRGN registers.
- ReqIF-WF.Type: Requirement

###### KQQA-FBEJ-DACC-DIGI_test: Test
This safety measure can be tested after the PROT owner has been configured using a write access to a protected register by a master agent function that is not the PROT owner.
- ReqIF-WF.Type: Requirement

###### KQQA-FBEJ-DACC-DIGI_reporting: Reporting
On detection of an access protection violation the RMEM will terminate the access with an SRI error that is detected by the XBAR, see SM[HW]:SRI:ERROR_HANDLING.
- ReqIF-WF.Type: Information

###### KQQA-FBEJ-DACC-DIGI_recommendederrorreaction: Recommended error reaction
System integrator to select an appropriate safe reaction in the SMU.
- ReqIF-WF.Type: Information

###### ZGLA-FBEJ-DACG-EBCH: SM[HW]:RMEM:CONTROL_REDUNDNACY
- IFX.Version: 3
- ReqIF-WF.Type: Heading

###### ZGLA-FBEJ-DACG-EBCH_description: Description
The control redundancy detects permanent and transient faults in the operation of a hardware element. Two symmetrical hardware modules perform duplicate operations and the results are compared. Any mismatch results in an error condition.
A hardware based self-test detects latent faults in the control redundancy mechanism and a software based test detects latent faults in the alarm.
The RMEM uses control redundancy to cover the logic that is not covered by SM[HW]:RMEM:READ_WRITE_ECC or SM[HW]:RMEM:SEP_TRANSACTION_INTEGRITY.
- ReqIF-WF.Type: Information

###### ZGLA-FBEJ-DACG-EBCH_resetoperationalstate: Reset operational state
This safety mechanism is enabled after application reset.
- ReqIF-WF.Type: Information

###### ZGLA-FBEJ-DACG-EBCH_configurationandactivation: Configuration and activation
N.A.
- ReqIF-WF.Type: Requirement

###### ZGLA-FBEJ-DACG-EBCH_test: Test
The control redundancy compare function provides the application software with the ability to generate an alarm by setting the redundantly encoded SCTRL.CMPTST = ON. This will inject an error into the comparators until it is set to OFF.
The following faults will be detected:
- A stuck at fault on the alarm signal path
- ReqIF-WF.Type: Requirement

###### ZGLA-FBEJ-DACG-EBCH_reporting: Reporting
If this safety mechanism detects a fault, the RMEM generates a RMEM control redundancy mismatch alarm.
- ReqIF-WF.Type: Information

###### ZGLA-FBEJ-DACG-EBCH_recommendederrorreaction: Recommended error reaction
System integrator to select appropriate safe reaction in SMU.
- ReqIF-WF.Type: Information

###### NLJA-FBEJ-DADD-CHBD: SM[HW]:SPU:READ_WRITE_ECC
- IFX.Version: 5
- ReqIF-WF.Type: Heading

###### NLJA-FBEJ-DADD-CHBD_description: Description
The RMEM implements EDC mechanisms to ensure data integrity within the RMEM.
Data paths between the SRI interface and the SRAM are redundantly encoded with an EDC and the EDC is checked at the destination.
- ReqIF-WF.Type: Information

###### NLJA-FBEJ-DADD-CHBD_resetoperationalstate: Reset operational state
This safety mechanism is enabled and active after application reset.
- ReqIF-WF.Type: Information

###### NLJA-FBEJ-DADD-CHBD_configurationandactivation: Configuration and activation
N.A.
- ReqIF-WF.Type: Requirement

###### NLJA-FBEJ-DADD-CHBD_test: Test
This safety mechanism can be tested by setting the SCTRL.GED bit-field to 1 B. This will inject an error on the next write access and trigger the alarm.
- ReqIF-WF.Type: Requirement

###### NLJA-FBEJ-DADD-CHBD_reporting: Reporting
On detection of a EDC violation the RMEM generates an RMEM internal EDC error alarm.
- ReqIF-WF.Type: Information

###### NLJA-FBEJ-DADD-CHBD_recommendederrorreaction: Recommended error reaction
System integrator to select appropriate safe reaction in SMU.
- ReqIF-WF.Type: Information

###### SOOA-FBEJ-DDDE-HEGG: SM[HW]:RMEM:SEP_TRANSACTION_INTEGRITY
- IFX.Version: 1
- ReqIF-WF.Type: Heading

###### SOOA-FBEJ-DDDE-HEGG_description: Description
The SEP interface implements redundancy and EDC mechanisms to ensure transaction integrity.
- All request, acknowledge and error signals are redundantly encoded with an inverted parity. The RMEM generates an alarm if it detects a parity error on the request signals
- On write accesses, the SPU generates an EDC covering the write address and data. The generated EDC is transmitted to the RMEM along with the write address and data. The RMEM performs an EDC check on the received write address and data and generates an alarm if the check fails
- ReqIF-WF.Type: Information

###### SOOA-FBEJ-DDDE-HEGG_resetoperationalstate: Reset operational state
This safety mechanism is enabled and active after application reset.
- ReqIF-WF.Type: Information

###### SOOA-FBEJ-DDDE-HEGG_configurationandactivation: Configuration and activation
Not applicable.
- ReqIF-WF.Type: Requirement

###### SOOA-FBEJ-DDDE-HEGG_test: Test
This safety mechanism can be tested by:
- Setting the SPU bit-field SM_USER.RMCTST to ON and executing an operation which results in the SPU generating a request to the RMEM. The SPU inserts a parity error on the request signals to the RMEM, which in turn results in the RMEM generating an SEP transaction integrity alarm
- ReqIF-WF.Type: Requirement

###### SOOA-FBEJ-DDDE-HEGG_reporting: Reporting
On detection of a parity or ECC violation on the SEP interface between the SPU or RDMA and RMEM, the RMEM generates a SEP transaction integrity alarm.
- ReqIF-WF.Type: Information

###### SOOA-FBEJ-DDDE-HEGG_recommendederrorreaction: Recommended error reaction
System integrator to select appropriate safe reaction in SMU.
- ReqIF-WF.Type: Information

##### FBTA-EIIF-DHIF-ECEI: Alarms
RMEM alarms
| Alarm name | Safety mechanism | Alarm flag to be cleared in |
| --- | --- | --- |
| RMEM internal EDC error | SM[HW]:RMEM:READ_WRITE_ECC | SMU only |
| RMEM control redundancy mismatch | SM[HW]:RMEM:CONTROL_REDUNDANCY | SMU only |
| RMEM SEP error | SM[HW]:RMEM:SEP_TRANSACTION_INTEGRITY | SMU only |
| SRI XBAR bus error alarm event | SM[HW]:RMEM:SV_AP SM[HW]:RMEM:CFG_AS_AP SM[HW]:RMEM:SAFETY_ENDINIT | SMU only |
| APU alarm | SM[HW]:RMEM:CFG_AS_AP SM[HW]:RMEM:SAFETY_ENDINIT | SMU only |
- IFX.Version: 1
- ReqIF-WF.Type: Information

##### RNTA-FAFF-HHHH-JGBJ: External safety mechanisms
- IFX.Version: 1
- ReqIF-WF.Type: Information

#### QNWA-EDEA-DJCF-DBGG: Stand-by Controller (SCR)
The standby controller is intended to perform basic operations while the rest of the system is in standby, effectively reducing standby-power consumption while still supporting requested standby features. The SCR is based on an 8-bit XC800-core with a limited list of peripherals.
Note: SCR is classified as a quality management product, therefore there are no safety mechanisms.
- IFX.Version: 1
- ReqIF-WF.Type: Information

##### WCNA-FAFF-HIBB-FDAE: Internal safety mechanisms
This section is not applicable for the module being described.
- IFX.Version: 1
- ReqIF-WF.Type: Information

##### TLIA-EHBA-BDCI-JHHB: Alarms
No safety alarms in SCR.
- IFX.Version: 1
- ReqIF-WF.Type: Information

##### HXWA-FAFF-HIBC-AAIJ: External safety mechanisms
This section is not applicable for the module being described.
- IFX.Version: 1
- ReqIF-WF.Type: Information

#### PDRA-EDEA-CIIC-CBBE: System Control Unit (SCU)
The System Control Unit (SCU) provides a collection of functions that are common for all CPUs like trap/NMI handling, Global overlay control and SOTA SWAP control, and various system functions that includes ERU cross-triggering, basic chip-information.
- IFX.Version: 1
- ReqIF-WF.Type: Information

##### XYGA-FAFF-HIED-FACJ: Internal safety mechanisms
- IFX.Version: 1
- ReqIF-WF.Type: Information

###### MVSA-EHEG-FHDA-FEAH: SM[HW]:SCU:REG_MONITOR
The SCU implements safety flip-flops for detecting transient or permanent faults in the configuration registers and sequential logic. The configuration and control registers, and bit-fields which are designed with safety flip-flops, are:
- TRAPS_CPU_CTRL
- TRAPS_CPU_SETCLRGRPg_SETCLREN(g=0-3)
- TRAPS_CPU_STAT
- TRAPS_CPU_DISy (y = 0-5)
- TRAPS_CS_CTRL
- TRAPS_CS_SETCLR_SETCLREN
- TRAPS_CS_STAT
- TRAPS_CS_DIS
- OVCENABLE
- SOTACTRL
- IFX.Version: 1
- ReqIF-WF.Type: Heading

###### MVSA-EHEG-FHDA-FEAH_description: Description
- ReqIF-WF.Type: Information

###### MVSA-EHEG-FHDA-FEAH_resetoperationalstate: Reset operational state
This safety mechanism is reset according to the reset behavior of each of the registers above, as specified in the Register Overview - SCU table in the User Manual.
- ReqIF-WF.Type: Information

###### MVSA-EHEG-FHDA-FEAH_configurationandactivation: Configuration and activation
N.A.
- ReqIF-WF.Type: Requirement

###### MVSA-EHEG-FHDA-FEAH_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### MVSA-EHEG-FHDA-FEAH_reporting: Reporting
Upon detection of an error, an alarm will be reported to the SMU.
Alarms triggered by the SFFs activate the global "SFF_ALARM".
- ReqIF-WF.Type: Information

###### MVSA-EHEG-FHDA-FEAH_recommendederrorreaction: Recommended error reaction
System integrator to select appropriate safe reaction in SMU.
- ReqIF-WF.Type: Information

###### HLEA-EHHJ-EGIG-EJGA: SM[HW]:SCU:ENDINIT
- IFX.Version: 1 1
- ReqIF-WF.Type: Heading

###### HLEA-EHHJ-EGIG-EJGA_description: Description
The SCU provides PROT mechanisms (PROTE, PROTCSE) that protect the configuration of the access protection mechanism (ACCEN). The ACCEN mechanism is based on the master agent function identifier. This supports freedom from interference of different SW tasks.
Unauthorized access attempts are blocked by this mechanism.
For a list of the registers protected by PROTE and PROTCSE, see tables 'Register overview – access mode glossary' and 'Register overview – SCU (ascending offset address)' in the User Manual.
- ReqIF-WF.Type: Information

###### HLEA-EHHJ-EGIG-EJGA_resetoperationalstate: Reset operational state
An application reset will set the configuration of this safety mechanism back to its default value.
- ReqIF-WF.Type: Information

###### HLEA-EHHJ-EGIG-EJGA_configurationandactivation: Configuration and activation
This safety mechanism is active after intentional configuration by application software through the PROTE and PROTCSE register.
- ReqIF-WF.Type: Requirement

###### HLEA-EHHJ-EGIG-EJGA_test: Test
This safety measure can be tested after the PROT owner has been configured:
Write access to a protected register by a master agent function that is not the PROT owner.
- ReqIF-WF.Type: Requirement

###### HLEA-EHHJ-EGIG-EJGA_reporting: Reporting
On detection of an access protection violation the SCU will terminate the access with FPI error that is detected by the BCU, see SM[HW]:FPI:ERROR_HANDLING.
- ReqIF-WF.Type: Information

###### HLEA-EHHJ-EGIG-EJGA_recommendederrorreaction: Recommended error reaction
System integrator to select an appropriate safe reaction in the SMU.
- ReqIF-WF.Type: Information

###### GUJA-EHHJ-EGIG-DCDE: SM[HW]:SCU:SV_AP
- IFX.Version: 4 4
- ReqIF-WF.Type: Heading

###### GUJA-EHHJ-EGIG-DCDE_description: Description
Critical module registers are implemented with a write access restriction that restricts the write access to access with supervisor (SV) privilege.
Unauthorized access attempts are blocked by this mechanism.
For a list of the registers protected by SV, see tables Register overview – access mode glossary and Register overview – SCU (ascending offset address) in the User Manual.
- ReqIF-WF.Type: Information

###### GUJA-EHHJ-EGIG-DCDE_resetoperationalstate: Reset operational state
The safety mechanism is active after application reset.
- ReqIF-WF.Type: Information

###### GUJA-EHHJ-EGIG-DCDE_configurationandactivation: Configuration and activation
N.A.
- ReqIF-WF.Type: Requirement

###### GUJA-EHHJ-EGIG-DCDE_test: Test
This safety measure can be tested by an write access to a protected register by a master agent function without supervisor (SV) access rights.
- ReqIF-WF.Type: Requirement

###### GUJA-EHHJ-EGIG-DCDE_reporting: Reporting
On detection of an access protection violation the SCU will terminate the access with FPI error that is detected by the BCU, see SM[HW]:FPI:ERROR_HANDLING.
- ReqIF-WF.Type: Information

###### GUJA-EHHJ-EGIG-DCDE_recommendederrorreaction: Recommended error reaction
System integrator to select an appropriate safe reaction in the SMU.
- ReqIF-WF.Type: Information

###### FRVA-EHHJ-EGIG-EFEH: SM[HW]:SCU:CFG_AS_AP
- IFX.Version: 4 4
- ReqIF-WF.Type: Heading

###### FRVA-EHHJ-EGIG-EFEH_description: Description
The SCU checks if the access master agent function identifier is enabled for the type of access (read access and write access, configured through the SCU ACCEN registers) to the selected register.
Unauthorized access attempts are blocked by this mechanism.
- ReqIF-WF.Type: Information

###### FRVA-EHHJ-EGIG-EFEH_resetoperationalstate: Reset operational state
An application reset will set the configuration of this safety mechanism back to its default value.
- ReqIF-WF.Type: Information

###### FRVA-EHHJ-EGIG-EFEH_configurationandactivation: Configuration and activation
This safety mechanism is active after intentional configuration by application software through the ACCENx registers.
- ReqIF-WF.Type: Requirement

###### FRVA-EHHJ-EGIG-EFEH_test: Test
This safety measure can be tested after the ACCENx has been configured:
Write access to a protected register by a master agent function that is not the ACCEN owner.
- ReqIF-WF.Type: Requirement

###### FRVA-EHHJ-EGIG-EFEH_reporting: Reporting
On detection of an access protection violation the SCU terminate the access with FPI error that is detected by the BCU, see SM[HW]:FPI:ERROR_HANDLING.
- ReqIF-WF.Type: Information

###### FRVA-EHHJ-EGIG-EFEH_recommendederrorreaction: Recommended error reaction
System integrator to select an appropriate safe reaction in the SMU.
- ReqIF-WF.Type: Information

###### LGDA-EHHJ-EGIG-FBAF: SM[HW]:SCU:SAFETY_ENDINIT
- IFX.Version: 9 9
- ReqIF-WF.Type: Heading

###### LGDA-EHHJ-EGIG-FBAF_description: Description
The SCU provides PROT mechanisms (PROTSE, PROTCSAE) that protect the configuration of the access protection mechanism (ACCEN). The ACCEN mechanism is based on the master agent function identifier. This supports freedom from interference of different SW tasks.
Unauthorized access attempts are blocked by this mechanism.
For a list of the registers protected by PROTSE and PROTCSAE, see tables 'Register overview – access mode glossary' and 'Register overview – SCU (ascending offset address)' in the User Manual.
- ReqIF-WF.Type: Information

###### LGDA-EHHJ-EGIG-FBAF_resetoperationalstate: Reset operational state
An application reset will set the configuration of this safety mechanism back to its default value.
- ReqIF-WF.Type: Information

###### LGDA-EHHJ-EGIG-FBAF_configurationandactivation: Configuration and activation
This safety mechanism is active after intentional configuration by application software through the PROTSE and PROTCSAE register.
- ReqIF-WF.Type: Requirement

###### LGDA-EHHJ-EGIG-FBAF_test: Test
This safety measure can be tested after the PROT owner has been configured:
Write access to a protected register by a master agent function that is not the PROT owner.
- ReqIF-WF.Type: Requirement

###### LGDA-EHHJ-EGIG-FBAF_reporting: Reporting
On detection of an access protection violation the SCU will terminate the access with FPI error that is detected by the BCU, see SM[HW]:FPI:ERROR_HANDLING.
- ReqIF-WF.Type: Information

###### LGDA-EHHJ-EGIG-FBAF_recommendederrorreaction: Recommended error reaction
System integrator to select an appropriate safe reaction in the SMU.
- ReqIF-WF.Type: Information

##### MIMA-EHBJ-DHGF-BAAD: Alarms
SCU alarms
| Alarm name | Safety mechanism | Alarm flag to be cleared in |
| --- | --- | --- |
| SCU SFF uncorrectable error alarm | SM[HW]:SCU:REG_MONITOR | SMU only |
| FPI error alarm | SM[HW]:SCU:SV_AP SM[HW]:SCUI:CFG_AS_AP SM[HW]:SCU:ENDINIT SM[HW]:SCU:SAFETY_ENDINIT | SMU only |
- IFX.Version: 1
- ReqIF-WF.Type: Information

##### PQAA-FAFF-HIEE-AECD: External safety mechanisms
- IFX.Version: 1
- ReqIF-WF.Type: Information

###### QLNA-EHEG-FHCG-EAJH: ESM[SW]:SCU:CONFIG_READBACK
The following registers of the reset configuration have to be read back after write. The read back values have to be compared with the written values. In case of any difference the Application Software shall trigger a reaction:
- TRAPS_CPU_SETCLRGRPg_SETCLREN (g=0-3)
- TRAPS_CPU_DISy (y = 0-5)
- ERU_EIFILT
- ERU_EICRx (x = 0-7)
- ERU_IGCRy (y = 0-7)
- OVCENABLE
- SOTACTRL
- IFX.Version: 1
- ReqIF-WF.Type: Heading

###### QLNA-EHEG-FHCG-EAJH_description: Description
- ReqIF-WF.Type: Requirement

#### VHZA-EDBI-IFBJ-IEBJ: System Direct Memory Access (SDMA)
The System DMA is a safe and flexible DMA controller capable of mastering data move operations without direct CPU involvement.
The System DMA, more commonly referred to as just the DMA, implements multiple master interfaces to the system interconnect, and contains two move engines to allow two data movement operations to run simultaneously. It also implements multiple DMA channels which undergo priority arbitration to become active in the move engines.
- IFX.Version: 1
- ReqIF-WF.Type: Information

##### GMAA-FABA-GFDB-GJIF: Internal safety mechanisms
- IFX.Version: 1
- ReqIF-WF.Type: Information

###### GSCA-EHEE-GJFH-GAAD: SM[HW]:DMA:LOCKSTEP
- IFX.Version: 19
- ReqIF-WF.Type: Heading

###### GSCA-EHEE-GJFH-GAAD_description: Description
The lockstep detects permanent and transient faults in the operation of a hardware element. Two symmetrical hardware modules perform duplicate operations in lockstep (or delayed by a fixed period) and the results are compared. Any mismatch results in an error condition.
A hardware based self-test detects latent faults in the lockstep and a software based test detects latent faults in the alarm.
The hardware element implements hardware redundancy by instancing two hardware modules known as the master and the checker, as well as a comparator. The two hardware modules use the same input data and perform the same function. During each clock cycle the comparator compares the master output against the checker output. If the comparator matches the master and checker output, the hardware element has performed the expected function. If there is a mismatch, the comparator has detected a fault in the operation of the hardware element and the comparator generates an alarm.
The lockstep is a variant of hardware redundancy that introduces a temporal separation between the master and checker:
- Every input to the checker is delayed by two clock cycles
- Every output from the master is delayed by two clock cycles
The comparator performs the output check two clock cycles after the master delivered the function output. The lockstep has no effect on the nominal operation.
Lockstep
- ReqIF-WF.Type: Information

###### GSCA-EHEE-GJFH-GAAD_resetoperationalstate: Reset operational state
This safety mechanism is enabled after application reset.
- ReqIF-WF.Type: Information

###### GSCA-EHEE-GJFH-GAAD_configurationandactivation: Configuration and activation
N.A.
- ReqIF-WF.Type: Requirement

###### GSCA-EHEE-GJFH-GAAD_test: Test
See SM[HW]:DMA:LOCKSTEP_SCC.
- ReqIF-WF.Type: Requirement

###### GSCA-EHEE-GJFH-GAAD_reporting: Reporting
If this safety mechanism detects a fault, the DMA generates a DMA lockstep mismatch alarm.
- ReqIF-WF.Type: Information

###### GSCA-EHEE-GJFH-GAAD_recommendederrorreaction: Recommended error reaction
System integrator to select appropriate safe reaction in SMU.
- ReqIF-WF.Type: Information

###### NJPA-EHEE-IDBB-HHCD: SM[HW]:DMA:LOCKSTEP_SCC
- IFX.Version: 1
- ReqIF-WF.Type: Heading

###### NJPA-EHEE-IDBB-HHCD_description: Description
The lockstep incorporates a hardware-based self-test. The self-test function sequentially injects faults into each comparator node. The lockstep detects that the fault was routed to the correct comparator node. If the fault was not routed to the correct comparator node or a real fault was detected, the lockstep generates an alarm.
The equivalent circuit for a lockstep comparator node with fault injection inputs is shown below. The self-test function injects faults into both the master and checker inputs of the critical outputs and qualified outputs.
Lockstep comparator node
The self-test function uses a free-running, binary counter using gray code number representation known as the input counter to calculate which comparator node will be tested in a given clock cycle. The self-test function will test every comparator node once every 8192 clock cycles. Alternate cycles of the self-test function will inject faults into either the master or checker side of a lockstep comparator node. A complete cycle of the self-test function will repeat every 16384 clock cycles. Injecting a fault into either side of a lockstep comparator node will cause the lockstep comparator node to fail unless a real fault occurs in the same clock cycle in which case the two faults will cancel out.
A second binary counter known as the monitor counter checks that the input counter has injected the fault into the intended lockstep comparator node. If the input counter and the monitor counter match the same comparator node and detect an injected fault, the lockstep will not generate an alarm. In the event a real fault has occurred the lockstep will generate an DMA lockstep mismatch alarm.
The following faults will be detected:
- An actual fault occurring at any of the master or checker inputs
- Includes the case of the actual fault coinciding with an injected fault
- A stuck at fault occurring at any of the comparator outputs
- A stuck at fault on signal x
- A stuck at fault on signal y
- A transient error occurring in the input counter
- A transient error occurring in the monitor counter
- ReqIF-WF.Type: Information

###### NJPA-EHEE-IDBB-HHCD_resetoperationalstate: Reset operational state
This safety mechanism is enabled after application reset.
- ReqIF-WF.Type: Information

###### NJPA-EHEE-IDBB-HHCD_configurationandactivation: Configuration and activation
N.A.
- ReqIF-WF.Type: Requirement

###### NJPA-EHEE-IDBB-HHCD_test: Test
The self-test function (triggered by setting LCLTEST.LCLT = 1) provides the application software with the ability to generate a lockstep alarm by injecting an error condition into the lockstep comparator.
The following faults will be detected:
- A stuck at fault on the alarm signal path
- ReqIF-WF.Type: Requirement

###### NJPA-EHEE-IDBB-HHCD_reporting: Reporting
If this safety mechanism detects a fault, the DMA generates an DMA lockstep mismatch alarm.
- ReqIF-WF.Type: Information

###### NJPA-EHEE-IDBB-HHCD_recommendederrorreaction: Recommended error reaction
System integrator to select appropriate safe reaction in SMU.
- ReqIF-WF.Type: Information

###### GDYA-ECIC-BHCC-JIGB: SM[HW]:DMA:SV
- IFX.Version: 1
- ReqIF-WF.Type: Heading

###### GDYA-ECIC-BHCC-JIGB_description: Description
Each DMA resource partition may be configured to perform DMA moves in user mode or supervisor (SV) mode. This allows access protection implemented at the slave functional blocks to report an error when it detects an unintended access on SV protected registers.
- ReqIF-WF.Type: Information

###### GDYA-ECIC-BHCC-JIGB_resetoperationalstate: Reset operational state
SM[HW]:DMA:SV is reset and disabled by application reset.
- ReqIF-WF.Type: Information

###### GDYA-ECIC-BHCC-JIGB_configurationandactivation: Configuration and activation
SM[HW]:DMA:SV is enabled when application software configures the following bit-fields in a DMA resource partition.
- MODEr.MODE - the user or supervisor mode for the DMA RP
- MODEr.VALID has to be configured to 1 B in order to mark the DMA RP as configured and valid
A DMA resource partition (RP) error interrupt may be enabled by writing EERr.ESER=1 B and EERr.EDER=1 B for source and destination errors respectively.
- ReqIF-WF.Type: Requirement

###### GDYA-ECIC-BHCC-JIGB_test: Test
The mechanism can be tested by configuring the DMA to access an SV protected register during a DMA move operation. For more information about SV protected registers refer to the "Register Overview" tables of the destination FB in the User Manual.
- ReqIF-WF.Type: Requirement

###### GDYA-ECIC-BHCC-JIGB_reporting: Reporting
On detection of an access protection violation, the accessed slave signals either a bus error to the system interconnect or signals an alarm to the SMU. If a bus error is signaled to the DMA, it reports either a source or destination error. If EERr.ESER is 1 B and the DMA reports a source error, the DMA also signals a DMA RP error interrupt. If EERr.EDER is 1 B and the DMA reports a destination error, the DMA also signals a DMA RP error interrupt.
- ReqIF-WF.Type: Information

###### GDYA-ECIC-BHCC-JIGB_recommendederrorreaction: Recommended error reaction
System integrator to select an appropriate safe reaction in the SMU or in response to the DMA RP error interrupt.
- ReqIF-WF.Type: Information

###### SCFA-ECIC-BHCC-JCJE: SM[HW]:DMA:STI
- IFX.Version: 1
- ReqIF-WF.Type: Heading

###### SCFA-ECIC-BHCC-JCJE_description: Description
Each DMA resource partition has a configurable master agent function identifier which is used for all DMA moves initiated by that DMA resource partition. This allows access protection implemented at the slave functional blocks to report an error when it detects an unintended access.
- ReqIF-WF.Type: Information

###### SCFA-ECIC-BHCC-JCJE_resetoperationalstate: Reset operational state
SM[HW]:DMA:STI is reset and disabled by application reset.
- ReqIF-WF.Type: Information

###### SCFA-ECIC-BHCC-JCJE_configurationandactivation: Configuration and activation
SM[HW]:DMA:STI is enabled when application software configures the following bit-fields in a DMA resource partition.
- MODEr.TAGOFF - the master agent function TAG identifier offset for the DMA RP
- MODEr.VMEN - whether the configured virtual machine information for the DMA RP is to be used at the slave functional block
- MODEr.VM - the virtual machine information for the DMA RP
- MODEr.PRSEN - whether the configured protection register set information for the DMA RP is to be used at the slave functional block
- MODEr.PRS - the protection register set information for the DMA RP
- MODEr.VALID has to be configured to 1 B in order to mark the DMA RP as configured and valid
A DMA RP error interrupt may be enabled by writing EERr.ESER=1 B and EERr.EDER=1 B for source and destination errors respectively.
- ReqIF-WF.Type: Requirement

###### SCFA-ECIC-BHCC-JCJE_test: Test
The mechanism can be tested by configuring the DMA to access a register protected by an Access Protection Unit (APU) during a DMA move operation.
- ReqIF-WF.Type: Requirement

###### SCFA-ECIC-BHCC-JCJE_reporting: Reporting
On detection of an access protection violation, the accessed slave signals either a bus error to the system interconnect or signals an alarm to the SMU. If a bus error is signaled to the DMA, it reports either a source or destination error. If EERr.ESER is 1 B and the DMA reports a source error, the DMA also signals a DMA RP error interrupt. If EERr.EDER is 1 B and the DMA reports a destination error, the DMA also signals a DMA RP error interrupt.
- ReqIF-WF.Type: Information

###### SCFA-ECIC-BHCC-JCJE_recommendederrorreaction: Recommended error reaction
System integrator to select an appropriate safe reaction in the SMU or in response to the DMA RP error interrupt.
- ReqIF-WF.Type: Information

###### VTGA-EHHA-FJJE-GDEC: SM[HW]:DMA:SAFETY_ENDINIT
- IFX.Version: 14 14
- ReqIF-WF.Type: Heading

###### VTGA-EHHA-FJJE-GDEC_description: Description
The DMA provides PROT mechanisms (PROTSE, PROTCSE) that protect the configuration of critical registers. The DMA also provides a unique PROT mechanism (PROTRPr) per DMA resource partition that protects the configuration of the resource partition access protection mechanism (ACCEN). The ACCEN mechanism is based on the master agent function identifier.
The PROT mechanisms support freedom from interference of different SW tasks. Unauthorized access attempts are blocked by these mechanisms.
For a list of the registers protected by PROTSE, PROTCSE and PROTRPr, see tables Register overview – access mode glossary and Register overview – DMA (ascending offset address) in the User Manual.
- ReqIF-WF.Type: Information

###### VTGA-EHHA-FJJE-GDEC_resetoperationalstate: Reset operational state
An application reset will set the configuration of this safety mechanism back to its default value.
- ReqIF-WF.Type: Information

###### VTGA-EHHA-FJJE-GDEC_configurationandactivation: Configuration and activation
This safety mechanism is active after intentional configuration by application software through the PROTSE, PROTCSE and PROTRPr registers.
- ReqIF-WF.Type: Requirement

###### VTGA-EHHA-FJJE-GDEC_test: Test
This safety measure can be tested after the PROT owner has been configured using a write access to a protected register by a master agent function that is not the PROT owner.
- ReqIF-WF.Type: Requirement

###### VTGA-EHHA-FJJE-GDEC_reporting: Reporting
On detection of an access protection violation on the FPI the DMA will terminate the access with an FPI error that is detected by the BCU, see SM[HW]:FPI:ERROR_HANDLING.
- ReqIF-WF.Type: Information

###### VTGA-EHHA-FJJE-GDEC_recommendederrorreaction: Recommended error reaction
System integrator to select an appropriate safe reaction in the SMU.
- ReqIF-WF.Type: Information

###### UAAA-EHHA-FJJE-IFAF: SM[HW]:DMA:SV_AP
- IFX.Version: 9 9
- ReqIF-WF.Type: Heading

###### UAAA-EHHA-FJJE-IFAF_description: Description
Critical module registers are implemented with a write access restriction that allows access only to masters with supervisor (SV) mode privilege.
Unauthorized access attempts are blocked by this mechanism.
For a list of the registers protected by SV, see tables Register overview – access mode glossary and Register overview – DMA (ascending offset address) in the User Manual.
- ReqIF-WF.Type: Information

###### UAAA-EHHA-FJJE-IFAF_resetoperationalstate: Reset operational state
The safety mechanism is active after application reset.
- ReqIF-WF.Type: Information

###### UAAA-EHHA-FJJE-IFAF_configurationandactivation: Configuration and activation
N.A.
- ReqIF-WF.Type: Requirement

###### UAAA-EHHA-FJJE-IFAF_test: Test
This safety measure can be tested by an write access to a protected register by a master agent function without supervisor (SV) access rights.
- ReqIF-WF.Type: Requirement

###### UAAA-EHHA-FJJE-IFAF_reporting: Reporting
On detection of an access protection violation the DMA will terminate the access with an FPI error that is detected by the BCU, see SM[HW]:FPI:ERROR_HANDLING.
- ReqIF-WF.Type: Information

###### UAAA-EHHA-FJJE-IFAF_recommendederrorreaction: Recommended error reaction
System integrator to select an appropriate safe reaction in the SMU.
- ReqIF-WF.Type: Information

###### FHMA-EHHA-FJJE-IJEG: SM[HW]:DMA:CFG_AS_AP
- IFX.Version: 1 1
- ReqIF-WF.Type: Heading

###### FHMA-EHHA-FJJE-IJEG_description: Description
The DMA provides a unique master agent function identifier based access protection mechanism (APU-Pr) per DMA resource partition that protects the configuration of the DMA resource partition and channel registers.
The DMA checks if the access master agent function identifier is enabled for the type of access (read access and write access, configured through the DMA ACCEN registers) to the selected register.
Unauthorized access attempts are blocked by this mechanism.
- ReqIF-WF.Type: Information

###### FHMA-EHHA-FJJE-IJEG_resetoperationalstate: Reset operational state
An application reset will set the configuration of this safety mechanism back to its default value.
- ReqIF-WF.Type: Information

###### FHMA-EHHA-FJJE-IJEG_configurationandactivation: Configuration and activation
This safety mechanism is active after intentional configuration by application software through the ACCENx registers.
- ReqIF-WF.Type: Requirement

###### FHMA-EHHA-FJJE-IJEG_test: Test
This safety measure can be tested after the ACCENRPr registers have been configured using an access to a protected register by a master agent function that is not enabled for the type of access configured by the DMA ACCENRPr registers.
- ReqIF-WF.Type: Requirement

###### FHMA-EHHA-FJJE-IJEG_reporting: Reporting
On detection of an access protection violation the DMA will terminate the access with an FPI error that is detected by the BCU, see SM[HW]:FPI:ERROR_HANDLING.
- ReqIF-WF.Type: Information

###### FHMA-EHHA-FJJE-IJEG_recommendederrorreaction: Recommended error reaction
System integrator to select an appropriate safe reaction in the SMU.
- ReqIF-WF.Type: Information

##### VFTA-EHBJ-CHGG-CGGA: Alarms
DMA alarms
| Alarm name | Safety mechanism | Alarm flag to be cleared in |
| --- | --- | --- |
| DMA lockstep mismatch alarm | - SM[HW]:DMA:LOCKSTEP - SM[HW]:DMA:LOCKSTEP_SCC | SMU only |
| DMA SRI transaction integrity alarm | - SM[HW]:SRI:SRI_TRANSACTION_INTEGRITY | SMU only |
| FPI error alarm | - SM[HW]:DMA:SV_AP - SM[HW]:DMA:CFG_AS_AP - SM[HW]:DMA:SAFETY_ENDINIT | SMU only |
- IFX.Version: 1
- ReqIF-WF.Type: Information

##### YLTA-FABA-GFEF-IHAE: External safety mechanisms
This section is not applicable for the module being described.
- IFX.Version: 1
- ReqIF-WF.Type: Information

#### LVUA-EDEA-DJAA-GGCA: System Mode Management (SMM)
The System Mode Management (SMM) and Reset Unit coordinate the system mode transitions including supply ramp-up, reset, start-up, operation, and ramp-down or standby states. The functional blocks PMS, PORTS, SMM, LBIST, SMU, CPU, PPU, CLOCKING and SSW interact to realize the various system states by triggering and propagating the transition events.
- ReqIF-WF.Type: Information

##### JTRA-FAFF-IJDI-IBEE: Internal safety mechanisms
- IFX.Version: 1
- ReqIF-WF.Type: Information

###### DXXA-EHEB-IIJE-EEHB: SM[HW]:SMM:REG_MONITOR
- IFX.Version: 1
- ReqIF-WF.Type: Heading

###### DXXA-EHEB-IIJE-EEHB_description: Description
The SMM implements safety flip-flops for detecting transient or permanent faults in the configuration registers and sequential logic. Safety flip-flops are special flip-flops that implement a hardware mechanism capable of detecting unexpected bit flip within the flip-flops. The configuration and control registers which are designed with safety flip-flops are listed below:
RSTTRIGCTRLA
RSTTRIGCTRLB
ESR0CFG
ESR0CNTCTRL
PDISC
DRVCFGESR0
DRVCFGESR1
STMEMx(x=1..2)
SHSEQCTRLB
SHSEQCTRLC
SWRSTCON
RSTSTAT
RSTSTATH
STCON
STSTAT
SYSCON
SHSEQCTRLA
SHSEQCTRLD
WRMRSTTRIG
WRMRSTTRIGH
RSTSTATBFW
- ReqIF-WF.Type: Information

###### DXXA-EHEB-IIJE-EEHB_resetoperationalstate: Reset operational state
This safety mechanism is reset according to the reset behavior of each of the registers above, as specified in the Register Overview - SMM table in the User Manual.
- ReqIF-WF.Type: Information

###### DXXA-EHEB-IIJE-EEHB_configurationandactivation: Configuration and activation
N.A.
- ReqIF-WF.Type: Requirement

###### DXXA-EHEB-IIJE-EEHB_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### DXXA-EHEB-IIJE-EEHB_reporting: Reporting
After the monitor detects a fault, an alarm will be reported on the SMM_REG_ALARM Alarm interface to the SMU.
- ReqIF-WF.Type: Information

###### DXXA-EHEB-IIJE-EEHB_recommendederrorreaction: Recommended error reaction
System integrator to select appropriate safe reaction in the SMU.
- ReqIF-WF.Type: Information

###### QTTA-EHDJ-IDEA-HAHF: SM[HW]:SMM:SAFE_FSM
- IFX.Version: 15
- ReqIF-WF.Type: Heading

###### QTTA-EHDJ-IDEA-HAHF_description: Description
The state machine in the logic of the Reset Controller of SMM is encoded using one hot coded state vectors to detect any unintended transitions caused by a bit-flip from one state to another without fulfilling the criteria for this state transition. Therefore any unexpected reset sequence execution is detected.
- ReqIF-WF.Type: Information

###### QTTA-EHDJ-IDEA-HAHF_resetoperationalstate: Reset operational state
This mechanism is reset by cold power-on reset.
- ReqIF-WF.Type: Information

###### QTTA-EHDJ-IDEA-HAHF_configurationandactivation: Configuration and activation
The safety mechanism is continuously active after cold power-on reset de-assertion.
- ReqIF-WF.Type: Requirement

###### QTTA-EHDJ-IDEA-HAHF_test: Test
This mechanism is tested through SM[HW]:MCU:LBIST and ESM[SW]:SMU:ALARM_SIGNAL_TEST.
- ReqIF-WF.Type: Requirement

###### QTTA-EHDJ-IDEA-HAHF_reporting: Reporting
In case of an unintended state transition the SMM_RESET_ALARM to the SMU is triggered.
- ReqIF-WF.Type: Information

###### QTTA-EHDJ-IDEA-HAHF_recommendederrorreaction: Recommended error reaction
System integrator to select appropriate safe reaction in the SMU.
- ReqIF-WF.Type: Information

###### NIEA-EHDA-BJEA-EJEH: SM[HW]:SMM:TIMEOUT_COUNTER
- IFX.Version: 1
- ReqIF-WF.Type: Heading

###### NIEA-EHDA-BJEA-EJEH_description: Description
The logic of the Reset Controller is protected by a timeout counter. In case of a blocked reset sequencing of a warm reset request the timeout counter ensures that after the time duration documented by the datasheet parameter tWARMRSTSEQ the requested reset is generated.
- ReqIF-WF.Type: Information

###### NIEA-EHDA-BJEA-EJEH_resetoperationalstate: Reset operational state
The mechanism is reset by cold power-on reset.
- ReqIF-WF.Type: Information

###### NIEA-EHDA-BJEA-EJEH_configurationandactivation: Configuration and activation
The timeout counter is active after any warm reset request.
- ReqIF-WF.Type: Requirement

###### NIEA-EHDA-BJEA-EJEH_test: Test
This safety mechanism is tested through SM[HW]:MCU:LBIST and ESM[SW]:SMU:ALARM_SIGNAL_TEST.
- ReqIF-WF.Type: Requirement

###### NIEA-EHDA-BJEA-EJEH_reporting: Reporting
In case of expiration of the timeout counter the SMM_RESET_ALARM to SMU is triggered.
- ReqIF-WF.Type: Information

###### NIEA-EHDA-BJEA-EJEH_recommendederrorreaction: Recommended error reaction
System integrator to select appropriate safe reaction in SMU.
- ReqIF-WF.Type: Information

###### UURA-EHDA-BJEG-JBGI: SM[HW]:SMM:REDUNDANT_CONTROL
- IFX.Version: 12
- ReqIF-WF.Type: Heading

###### UURA-EHDA-BJEG-JBGI_description: Description
The kernel reset logic in all modules are protected from unintended module reset by two kernel reset request bits (RST_CTRLA.KRST & RST_CTRLB.KRST). Both have to be set to trigger a kernel reset. Therefore an error in one of both bits or setting only one bit does not lead to a kernel reset execution. Thus a fault is prevented.
- ReqIF-WF.Type: Information

###### UURA-EHDA-BJEG-JBGI_resetoperationalstate: Reset operational state
This mechanism is reset by system reset.
- ReqIF-WF.Type: Information

###### UURA-EHDA-BJEG-JBGI_configurationandactivation: Configuration and activation
N.A.
- ReqIF-WF.Type: Requirement

###### UURA-EHDA-BJEG-JBGI_test: Test
N.A.
- ReqIF-WF.Type: Requirement

###### UURA-EHDA-BJEG-JBGI_reporting: Reporting
N.A.
- ReqIF-WF.Type: Information

###### UURA-EHDA-BJEG-JBGI_recommendederrorreaction: Recommended error reaction
N.A.
- ReqIF-WF.Type: Information

###### RDZA-EHHJ-EHFH-CJCD: SM[HW]:SMM:ENDINIT
- IFX.Version: 1 1
- ReqIF-WF.Type: Heading

###### RDZA-EHHJ-EHFH-CJCD_description: Description
The SMM provides PROT mechanisms (PROTE, PROTCE) that protect the configuration of the access protection mechanism (ACCEN). The ACCEN mechanism is based on the master agent function identifier. This supports freedom from interference of different SW tasks.
Unauthorized access attempts are blocked by this mechanisms.
For a list of the registers protected by PROTE and PROTCE, see tables Register overview – access mode glossary and Register overview – SMM (ascending offset address) in the User Manual.
- ReqIF-WF.Type: Information

###### RDZA-EHHJ-EHFH-CJCD_resetoperationalstate: Reset operational state
An application reset will set the configuration of this safety mechanism back to its default value.
- ReqIF-WF.Type: Information

###### RDZA-EHHJ-EHFH-CJCD_configurationandactivation: Configuration and activation
This safety mechanism is active after intentional configuration by application software through the PROTE and PROTCE registers.
- ReqIF-WF.Type: Requirement

###### RDZA-EHHJ-EHFH-CJCD_test: Test
This safety measure can be tested after the PROT owner has been configured:
Write access to a protected register by a master agent function that is not the PROT owner.
- ReqIF-WF.Type: Requirement

###### RDZA-EHHJ-EHFH-CJCD_reporting: Reporting
On detection of an access protection violation the SMM will terminate the access with FPI error that is detected by the BCU, see SM[HW]:FPI:ERROR_HANDLING.
- ReqIF-WF.Type: Information

###### RDZA-EHHJ-EHFH-CJCD_recommendederrorreaction: Recommended error reaction
System integrator to select an appropriate safe reaction in the SMU.
- ReqIF-WF.Type: Information

###### ZAKA-EHHJ-EHFH-DBAB: SM[HW]:SMM:SAFETY_ENDINIT
- IFX.Version: 1 1
- ReqIF-WF.Type: Heading

###### ZAKA-EHHJ-EHFH-DBAB_description: Description
The SMM provides a PROT mechanism (PROTCPUn) that protects the configuration of the PMCSRn register. The SMM also provides PROT mechanisms (PROTSE, PROTCSE) that protect the configuration of the access protection mechanism (ACCEN). The ACCEN mechanism is based on the master agent function identifier.
The PROT mechanisms support freedom from interference of different SW tasks.
Unauthorized access attempts are blocked by these mechanisms.
For a list of the registers protected by PROTSE, PROTCSE and PROTCPUn, see tables Register overview – access mode glossary and Register overview – SMM (ascending offset address) in the User Manual.
- ReqIF-WF.Type: Information

###### ZAKA-EHHJ-EHFH-DBAB_resetoperationalstate: Reset operational state
An application reset will set the configuration of this safety mechanism back to its default value.
- ReqIF-WF.Type: Information

###### ZAKA-EHHJ-EHFH-DBAB_configurationandactivation: Configuration and activation
This safety mechanism is active after intentional configuration by application software through the PROTSE, PROTCSE and PROTCPUn registers.
- ReqIF-WF.Type: Requirement

###### ZAKA-EHHJ-EHFH-DBAB_test: Test
This safety measure can be tested after the PROT owner has been configured using a write access to a protected register by a master agent function that is not the PROT owner.
- ReqIF-WF.Type: Requirement

###### ZAKA-EHHJ-EHFH-DBAB_reporting: Reporting
On detection of an access protection violation the SMM will terminate the access with FPI error that is detected by the BCU, see SM[HW]:FPI:ERROR_HANDLING.
- ReqIF-WF.Type: Information

###### ZAKA-EHHJ-EHFH-DBAB_recommendederrorreaction: Recommended error reaction
System integrator to select an appropriate safe reaction in the SMU.
- ReqIF-WF.Type: Information

###### WXDA-EHHJ-EHFH-CFCI: SM[HW]:SMM:CFG_AS_AP
- IFX.Version: 5 5
- ReqIF-WF.Type: Heading

###### WXDA-EHHJ-EHFH-CFCI_description: Description
The SMM checks if the access master agent function identifier is enabled for the type of access (read access and write access, configured through the SMM ACCEN registers) to the selected register.
Unauthorized access attempts are blocked by this mechanism.
- ReqIF-WF.Type: Information

###### WXDA-EHHJ-EHFH-CFCI_resetoperationalstate: Reset operational state
An application reset will set the configuration of this safety mechanism back to its default value.
- ReqIF-WF.Type: Information

###### WXDA-EHHJ-EHFH-CFCI_configurationandactivation: Configuration and activation
This safety mechanism is active after intentional configuration by application software through the ACCENx registers.
- ReqIF-WF.Type: Requirement

###### WXDA-EHHJ-EHFH-CFCI_test: Test
This safety measure can be tested after the ACCENx has been configured:
Write access to a protected register by a master agent function that is not the ACCEN owner.
- ReqIF-WF.Type: Requirement

###### WXDA-EHHJ-EHFH-CFCI_reporting: Reporting
On detection of an access protection violation the SMM terminate the access with FPI error that is detected by the BCU, see SM[HW]:FPI:ERROR_HANDLING.
- ReqIF-WF.Type: Information

###### WXDA-EHHJ-EHFH-CFCI_recommendederrorreaction: Recommended error reaction
System integrator to select an appropriate safe reaction in the SMU.
- ReqIF-WF.Type: Information

###### GBVA-EHHJ-EHFH-ABDG: SM[HW]:SMM:SV_AP
- IFX.Version: 5 5
- ReqIF-WF.Type: Heading

###### GBVA-EHHJ-EHFH-ABDG_description: Description
Critical module registers are implemented with a write access restriction that restricts the write access to access with supervisor (SV) privilege.
Unauthorized access attempts are blocked by this mechanism.
For a list of the registers protected by SV, see tables Register overview – access mode glossary and Register overview – SMM (ascending offset address) in the User Manual.
- ReqIF-WF.Type: Information

###### GBVA-EHHJ-EHFH-ABDG_resetoperationalstate: Reset operational state
The safety mechanism is active after application reset.
- ReqIF-WF.Type: Information

###### GBVA-EHHJ-EHFH-ABDG_configurationandactivation: Configuration and activation
N.A.
- ReqIF-WF.Type: Requirement

###### GBVA-EHHJ-EHFH-ABDG_test: Test
This safety measure can be tested by an write access to a protected register by a master agent function without supervisor (SV) access rights.
- ReqIF-WF.Type: Requirement

###### GBVA-EHHJ-EHFH-ABDG_reporting: Reporting
On detection of an access protection violation the SMM will terminate the access with FPI error that is detected by the BCU, see SM[HW]:FPI:ERROR_HANDLING.
- ReqIF-WF.Type: Information

###### GBVA-EHHJ-EHFH-ABDG_recommendederrorreaction: Recommended error reaction
System integrator to select an appropriate safe reaction in the SMU.
- ReqIF-WF.Type: Information

###### WKVA-FJBG-DDGJ-IFGA: SM[HW]:SMM:STARTUP_PROTECTION
- IFX.Version: 1
- ReqIF-WF.Type: Heading

###### WKVA-FJBG-DDGJ-IFGA_description: Description
The SMM provides a startup protection mechanism (STP) that protects application critical SMM functions which were installed during the MCU boot operation to support freedom from interference measures of different software tasks. Registers which are protected by STP can only be accessed before the start-up protection is set (SMM_STCON.ST_PROT=1). The ST_PROT bit is set by Boot Firmware before releasing the control to user software.
- ReqIF-WF.Type: Information

###### WKVA-FJBG-DDGJ-IFGA_resetoperationalstate: Reset operational state
This mechanism is active after application reset.
- ReqIF-WF.Type: Information

###### WKVA-FJBG-DDGJ-IFGA_configurationandactivation: Configuration and activation
Start-up protection is automatically activated after any successful boot operation.
- ReqIF-WF.Type: Requirement

###### WKVA-FJBG-DDGJ-IFGA_test: Test
The mechanism can be tested by executing an access on an STP protected register.
- ReqIF-WF.Type: Requirement

###### WKVA-FJBG-DDGJ-IFGA_reporting: Reporting
On detection of an access protection violation the SMM signals Bus Error to the Interconnect. The FPI BCU in the Interconnect signals an Alarm_NCS or Alarm_CS alarm to SMU or SMU_CS (depending if the cause of the error was security critical) as a response to the Bus Error.
- ReqIF-WF.Type: Information

###### WKVA-FJBG-DDGJ-IFGA_recommendederrorreaction: Recommended error reaction
System integrator to select appropriate safe reaction in SMU.
- ReqIF-WF.Type: Information

##### BMRA-EHBJ-DIFB-FECE: Alarms
SMM alarms
| Alarm name | Safety mechanism | Alarm flag to be cleared in |
| --- | --- | --- |
| SMM_REG_ALARM | SM[HW]:SMM:REG_MONITOR | SMU only |
| SMM_RESET_ALARM | SM[HW]:SMM:SAFE_FSM | SMU only |
| SMM_RESET_ALARM | SM[HW]:SMM:TIMEOUT:COUNTER | SMU only |
| FPI error alarm | SM[HW]:SMM:SV_AP SM[HW]:SMM:CFG_AS_AP SM[HW]:SMM:ENDINIT SM[HW]:SMM:SAFETY_ENDINIT | SMU only |
- IFX.Version: 1
- ReqIF-WF.Type: Information

##### BACA-FAFF-IJEJ-DJHB: External safety mechanisms
- IFX.Version: 1
- ReqIF-WF.Type: Information

###### IDOA-EHDA-BJFA-GDIB: ESM[SW]:SMM:CONFIG_READBACK
- IFX.Version: 1
- ReqIF-WF.Type: Heading

###### IDOA-EHDA-BJFA-GDIB_description: Description
The following registers of the reset configuration have to be read back after writing to assure the correct content it written to the SFF protected registers. Unintentional bit flips after successful write are covered by safety flip-flops. The read back values have to be compared with the written values. In case of any difference the Application Software shall trigger a reaction.
RSTTRIGCTRLA
RSTTRIGCTRLB
ESR0CFG
ESRCFGx
ESR0CNTCTRL
PDISC
DRVCFGESR0
DRVCFGESR1
1
- ReqIF-WF.Type: Requirement

#### FBYA-EDCJ-EFHF-HCDD: Safety and security alarm Management Unit (SMU)
As a central component of the safety and security architecture, the SMU provides a generic interface to manage the behavior of the microcontroller under the presence of safety critical faults and security events. These faults and security events are signaled to the SMU as alarms. Each alarm can be individually configured to trigger internal reactions and notify externally through a fault signaling protocol.
- IFX.Version: 1
- ReqIF-WF.Type: Information

##### JETA-FAFF-IJHG-AAGC: Internal safety mechanisms
- IFX.Version: 1
- ReqIF-WF.Type: Information

###### CGSA-FJFC-JIHG-GHIH: SM[HW]:SMU:ALIVE_MONITOR
- IFX.Version: 1
- ReqIF-WF.Type: Heading

###### CGSA-FJFC-JIHG-GHIH_description: Description
The Alive Monitors detect transient or permanent faults in alarm reaction generation of SMU_SAFE0, SMU_SAFE1 and SMU_CS. Upon detection of faults, corresponding Alive Alarm is triggered and processed in SMU_STDBY.
The SMU_SAFE0 Alive Alarm will be triggered if one of the following conditions is met:
- An alarm event occurs while the SMU_SAFE0 is in RUN or FAULT state and the SMU_SAFE0 Alive Monitor detects that a reaction has not been generated by the SMU_SAFE0
- An alarm reaction has been generated by the SMU_SAFE0 in RUN or FAULT state and SMU_SAFE0 Alive Monitor detects that no alarm event has occurred
- A watchdog or recovery timer alarm event occurs while the SMU_SAFE0 is in START state and the SMU_SAFE0 Alive Monitor detects that a reaction has not been generated by the SMU_SAFE0
Independent Alive Monitors are present in SMU_SAFE1 and SMU_CS. The trigger conditions explained above can also be mapped to SMU_SAFE1 and SMU_CS with the only exception that for SMU_CS there is no FAULT state.
- ReqIF-WF.Type: Information

###### CGSA-FJFC-JIHG-GHIH_resetoperationalstate: Reset operational state
The safety mechanism is active from application reset on.
- ReqIF-WF.Type: Information

###### CGSA-FJFC-JIHG-GHIH_configurationandactivation: Configuration and activation
N.A.
- ReqIF-WF.Type: Requirement

###### CGSA-FJFC-JIHG-GHIH_test: Test
Application software shall, at least once per driving cycle, configure SMU_SAFE0, SMU_SAFE1 and SMU_CS to test corresponding Alive Alarms. From each instance independently following software routine should be run to test the Alive Alarms :
- Writing the SMU_AliveTest(0x5) command
- This will trigger the Alive Monitor to inject a fault and forward the Alive Alarm to the SMU_STDBY
- The corresponding Alive Alarm flag can be read from the register AGSTDBYi_STS (Refer to ProductAlarm Mapping Tables) to check whether Alarm has been triggered
- The Alive Monitor error injection can be disabled by writing the SMU_AliveTest(0xA) command. However, the SMU_AliveTest(0xA) command cannot clear the corresponding alive alarm when the alarm is generated by a real fault. An application reset (at least) is needed to clear the Alive Alarm
- ReqIF-WF.Type: Requirement

###### CGSA-FJFC-JIHG-GHIH_reporting: Reporting
Fault reporting via SMU_SAFE0 Alive Alarm, SMU_SAFE1 Alive Alarm and SMU_CS Alive Alarm to SMU_STDBY.
- ReqIF-WF.Type: Information

###### CGSA-FJFC-JIHG-GHIH_recommendederrorreaction: Recommended error reaction
It is recommended upon reception of the alarm event that the SMU_STDBY indicates the FAULT state on one or more FSP pins.
- ReqIF-WF.Type: Information

###### OVGA-FJFC-BBGJ-DDFE: SM[HW]:SMU:FSP_MONITOR
- IFX.Version: 1
- ReqIF-WF.Type: Heading

###### OVGA-FJFC-BBGJ-DDFE_description: Description
SMU_SAFE0 and SMU_SAFE1 provides FSP monitors for their corresponding FSP Layers to detect unintended FAULT state activation. As soon as activation of FAULT state happens corresponding Fault State Activation Alarm is triggered and processed by either SMU_SAFE0 or SMU_SAFE1.
- ReqIF-WF.Type: Information

###### OVGA-FJFC-BBGJ-DDFE_resetoperationalstate: Reset operational state
The safety mechanism is active from application reset on.
- ReqIF-WF.Type: Information

###### OVGA-FJFC-BBGJ-DDFE_configurationandactivation: Configuration and activation
N.A.
- ReqIF-WF.Type: Requirement

###### OVGA-FJFC-BBGJ-DDFE_test: Test
Software Alarms can be used to test the FSP monitor. One of such scenarios is explained below:
- Initial Configuration: SMU_SAFE0 is initialized and configured as described in SMU chapter in the User Manual. Beside the normal configuration for FSP using register SAFE0_FSP0_CON, Software Alarm 0 is mapped to generate external reaction of FAULT state indication on FSP0 by setting SAFE0_AGSF10_FSP0 = 0x1
- Run-time Behavior: Application software writes the SMU_Alarm(0x0) command (write SAFE0_CMD = 0x6) to trigger Software Alarm 0. SMU_SAFE0 triggers FAULT state indication on FSP0 as well as 'SMU_SAFE0 FSP0 Fault State Activation Alarm' shall be triggered. Correspondingly SAFE0_AGSF10_STS.SF16 will be set
- ReqIF-WF.Type: Requirement

###### OVGA-FJFC-BBGJ-DDFE_reporting: Reporting
SMU_SAFE0 FSP0 Fault State Activation Alarm, SMU_SAFE0 FSP1 Fault State Activation Alarm, SMU_SAFE1 FSP2 Fault State Activation Alarm, SMU_SAFE1 FSP3 Fault State Activation Alarm
- ReqIF-WF.Type: Information

###### OVGA-FJFC-BBGJ-DDFE_recommendederrorreaction: Recommended error reaction
It is recommended upon reception of the alarm event, SMU_SAFE0 or SMU_SAFE1 is configured to generate reactions like NMI[0:3] or IRQ[0:5] so that application software shall perform plausibility check by reading the alarm status registers SAFEx_AGSFi_STS and SAFEx_AGSHi_STS.
- ReqIF-WF.Type: Information

###### EYFA-EHDJ-IGEB-DJDJ: SM[HW]:SMU:CRITICAL_ALARM
- IFX.Version: 1
- ReqIF-WF.Type: Heading

###### EYFA-EHDJ-IGEB-DJDJ_description: Description
Beside static alarm mapping for diverse processing of alarms within SM[HW]:SMU:DIVERSE_REDUNDANCY, SMU_SAFE0 also provides the application software with the ability to map one or more incoming alarms to one SMU_SAFE0 Critical Alarm. The SMU_SAFE0 Critical Alarm is processed in SMU_STDBY.
Similarly SMU_SAFE1 and SMU_CS can also trigger their corresponding SMU_SAFE1 Critical Alarm and SMU_CS Critical Alarm.
- ReqIF-WF.Type: Information

###### EYFA-EHDJ-IGEB-DJDJ_resetoperationalstate: Reset operational state
The safety mechanism is active from application reset on. However after application reset all of the critical alarm selection registers are initialized with 0, which means that no incoming alarm is mapped to critical alarm.
- ReqIF-WF.Type: Information

###### EYFA-EHDJ-IGEB-DJDJ_configurationandactivation: Configuration and activation
The application software has to configure SAFE0_AGCSi_CAS and SAFE0_AGSHi_CAS registers to define the user specific critical alarm mapping.
The application software has to configure SAFE1_AGCSi_CAS and SAFE1_AGSHi_CAS for SMU_SAFE1 specific critical alarm mapping, while for SMU_CS, CS_AGCSi_CAS and CS_AGSHi_CAS has to be configured.
- ReqIF-WF.Type: Requirement

###### EYFA-EHDJ-IGEB-DJDJ_test: Test
Software Alarms can be used to test the critical alarm generation. One of such scenarios is explained below:
- Initial Configuration: SMU_SAFE0 and SMU_STDBY is initialized and configured as described in the SMU chapter in the User Manual. Software Alarm 0 is configured to trigger critical alarm by setting SAFE0_AGSF10_CAS = 0x1
- Run-time Behavior: Application software writes the SMU_Alarm(0x0) command (write SAFE0_CMD = 0x6) to trigger Software Alarm 0. SMU_SAFE0 triggers 'SMU_SAFE0 Critical Alarm'. Correspondingly AGSTDBY4_STS.SF4 will be set
- ReqIF-WF.Type: Requirement

###### EYFA-EHDJ-IGEB-DJDJ_reporting: Reporting
SMU_SAFE0 Critical Alarm, SMU_SAFE1 Critical Alarm and SMU_CS Critical Alarm to SMU_STDBY
- ReqIF-WF.Type: Information

###### EYFA-EHDJ-IGEB-DJDJ_recommendederrorreaction: Recommended error reaction
It is recommended upon reception of the alarm event, SMU_STDBY is configured to indicate FAULT state on one or more FSP pins.
- ReqIF-WF.Type: Information

###### CSRA-EHDJ-IHDF-ICIH: SM[HW]:SMU:RT
- IFX.Version: 1
- ReqIF-WF.Type: Heading

###### CSRA-EHDJ-IHDF-ICIH_description: Description
Recovery timer instances are available to monitor the response time of internal reactions triggered by an alarm. If a recovery timer is enabled, upon detection of any mapped alarm event the recovery timer starts and counts until application software stops it with the SMU_RTStop() command. If the SMU does not receive the SMU_RTStop() command and the recovery timer expires, an internal SMU alarm (RTx Time-out Alarm) is issued. The use of the recovery timer only makes sense if the internal reaction is an interrupt or NMI. A detail description about the usage of the recovery timer can be found in the SMU chapter (SMU_SAFE and SMU_CS Recovery Timer sections) of user manual.
In SMU_SAFE0 two RT instances (RT0 and RT1) are available. Moreover in SMU_SAFE1 two independent RT instances are also available. In SMU_CS only one instance of RT is available. Each RT instance shall trigger independent RT time-out alarms.
- ReqIF-WF.Type: Information

###### CSRA-EHDJ-IHDF-ICIH_resetoperationalstate: Reset operational state
After application reset all of the RT instances are disabled except the RT instances in SMU_SAFE0 which are enabled by default to serve CPU watchdogs alarms.
- ReqIF-WF.Type: Information

###### CSRA-EHDJ-IHDF-ICIH_configurationandactivation: Configuration and activation
Application software can map maximum of 4 alarms to a single RT instance using registers SAFE0_RTiACA and SAFE0_RTiACB (where i is RT instance). Application software shall enable the RT using bitfield SAFE0_RTC.RiE (where i is RT instance) and configure the RT timeout duration using bitfields SAFE0_RTC.PRE and SAFE0_RTC.RTD.
For SMU_SAFE1, registers SAFE1_RTiACA, SAFE1_RTiACB and SAFE1_RTC can be used to configure RT instances. However in SMU_CS, CS_RTiACA, CS_RTiACB and CS_RTC can be used to configure RT instance.
- ReqIF-WF.Type: Requirement

###### CSRA-EHDJ-IHDF-ICIH_test: Test
Software Alarms can be used to test the recovery timer. One of such scenario is explained below:
- Initial Configuration: SMU_SAFE0 is initialized and configured as described in SMU chapter in the User Manual. Software Alarm 0 is configured to trigger NMI0 and also recovery timer 0 (RT0). SMU_SAFE0 RT0 Time-out Alarm is configured to trigger NMI1. Moreover a known RT0 timeout duration is configured in SAFE0_RTC
- Run-time Behavior: Application software writes the SMU_Alarm(0x0) command (write SAFE0_CMD = 0x6) to trigger Software Alarm 0. SMU_SAFE0 triggers NMI0 as well as starts RT0. If the SMU does not receive the SMU_RTStop(0x0) command and the RT0 expires, then NMI1 will be triggered by SMU_SAFE0 RT0 Time-out Alarm. Application software checks the time difference between NMI0 and NMI1, and correlates the corresponding time difference with configured RT0 timeout duration to test the RT0
- ReqIF-WF.Type: Requirement

###### CSRA-EHDJ-IHDF-ICIH_reporting: Reporting
Recovery timers time-out signaling via SMU_SAFE0 RT0 Time-out Alarm and SMU_SAFE0 RT1 Time-out Alarm to SMU_SAFE0.
Recovery timers time-out signaling via SMU_SAFE1 RT0 Time-out Alarm and SMU_SAFE1 RT1 Time-out Alarm to SMU_SAFE1.
Recovery timer time-out signaling via SMU_CS RT0 Time-out Alarm to SMU_CS.
- ReqIF-WF.Type: Information

###### CSRA-EHDJ-IHDF-ICIH_recommendederrorreaction: Recommended error reaction
If the recovery timer (RT) is monitoring the response time of internal reactions like IRQx (x=0-5) or NMIy (y=0-3) it is recommended that RT time-out alarm shall be configured to generate reaction like RESETx_REQ along with external reaction of FAULT state indication on FSP from SMU_SAFE0 and SMU_SAFE1.
- ReqIF-WF.Type: Information

###### PGBA-EHDA-AJIJ-IADI: SM[HW]:SMU:LOCK
- IFX.Version: 10
- ReqIF-WF.Type: Heading

###### PGBA-EHDA-AJIJ-IADI_description: Description
A configuration locking mechanism is implemented within SMU instances SMU_SAFE0, SMU_SAFE1, SMU_GCC and SMU_CS. Once the configuration is locked by the internal locking mechanism, any write request to the configuration registers will not update the registers.
The SMU_SAFEx (x = 0,1) configuration registers controlled by the SAFEx_KEYS register properties are:
- SAFEx_FSPi_CON (where x = 0-1; i = 0-1)
- SAFEx_PES (where x = 0-1)
- SAFEx_AGC (where x = 0-1)
- SAFEx_RTC (where x = 0-1)
- SAFEx_RT0ACA (where x = 0-1)
- SAFEx_RT0ACB (where x = 0-1)
- SAFEx_RT1ACA (where x = 0-1)
- SAFEx_RT1ACB (where x = 0-1)
- SAFEx_AGSFi_CONj, SAFEx_AGSFi_CAS and SAFEx_AGSFi_FSPj (where x = 0-1; i = 0-13; j = 0-3)
- SAFEx_AGSHi_CONj, SAFEx_AGSHi_CAS and SAFEx_AGSHi_FSPj (where x = 0-1; i = 0-2; j = 0-3)
- SAFEx_PCTL (where x = 0-1)
- SAFEx_KEYS (where x = 0-1)
The SAFEx_CMD (where x = 0-1) register is not locked as it is used for run-time hardware/software interaction, it is not a configuration register.
The SAFEx_AGSFi_STS (where x = 0-1; i = 0-13) and SAFEx_AGSHi_STS (where x = 0-1; i = 0-2) registers are not locked as it is possible during run-time to clear the alarm by software.
The SAFEx_AEXCLR (where x = 0-1) register is not locked as it is possible during run-time to clear the SAFEx_AEX (where x = 0-1).
The read only registers of SMU_SAFEx (x = 0,1) do not need to be protected by lock mechanism.
The SMU configuration registers controlled by the GCC_KEYS register properties are:
- GCC_EMSR
- GCC_RMi_CTL (where i = 0-4)
- GCC_AGSHi_SEL (where i = 0-2)
- GCC_KEYS
The GCC_EMSSW register is not locked as it is used for run-time hardware/software interaction, it is not a configuration register.
The OCS do not belong to the SMU_GCC kernel but to the standard bus interface module, therefore they can’t be controlled by the GCC_KEYS register.
The read only registers of SMU_GCC do not need to be protected by lock mechanism.
The SMU configuration registers controlled by the CS_KEYS register properties are:
- CS_RTC
- CS_RT0ACA
- CS_RT0ACB
- CS_AGCSi_CONj and CS_AGCSi_CAS (where i = 0-1; j = 0-2)
- CS_AGSHi_CONj and CS_AGSHi_CAS (where i = 0-2; j = 0-2)
- CS_AGSHi_SEL (where i = 0-2)
- CS_KEYS
The CS_CMD register is not locked as it is used for run-time hardware/software interaction, it is not a configuration register.
The CS_AGCSi_STS (where i = 0-1) and CS_AGSHiSTS (where i = 0-2) registers are not locked as it is possible during run-time to clear the alarm by software.
The CS_AEXCLR register is not locked as it is possible during run-time to clear the CS_AEX.
The read only registers of SMU_CS do not need to be protected by lock mechanism.
- ReqIF-WF.Type: Information

###### PGBA-EHDA-AJIJ-IADI_resetoperationalstate: Reset operational state
After application reset CFGLCK and PERLCK fields of the SAFEx_KEYS are set to 0x00.
After application reset CFGLCK and PERLCK fields of the GCC_KEYS are set to 0x00.
After application reset CFGLCK and PERLCK fields of the CS_KEYS are set to 0x00.
- ReqIF-WF.Type: Information

###### PGBA-EHDA-AJIJ-IADI_configurationandactivation: Configuration and activation
In order to configure and lock the SMU_SAFEx (x=0,1) configuration the following steps shall be followed:
- The SMU_SAFEx (x = 0,1) configuration is only possible if the CFGLCK field of the SAFEx_KEYS register is set to 0xBC
- After SMU_SAFEx (x = 0,1) configuration is done, CFGLCK field should be set to any other value beside 0xBC, for example 0x00, for locking the configuration
- If the PERLCK field of the SAFEx_KEYS register is set to 0xFF no further SMU_SAFEx (x = 0,1) configuration is possible, including the SAFEx_KEYS register itself. SMU_SAFEx (x = 0,1) configuration is possible again after the PERLCK field of the SAFEx_KEYS register is reset to 0x00 by an application reset
Although CFGLCK field can be set to 0xBC during any SMU_SAFE0/1 state (with the exception of permanent lock using PERLCK=0xFF), it is recommended to configure and lock the SMU_SAFE0/1 configuration during START state.
In order to configure and lock the SMU_GCC configuration the following steps shall be followed:
- The SMU_GCC configuration is only possible if the CFGLCK field of the GCC_KEYS register is set to 0xBC
- After SMU_GCC configuration is done, CFGLCK field should be set to any other value beside 0xBC, for example 0x00, for locking the configuration
- If the PERLCK field of the GCC_KEYS register is set to 0xFF no further SMU_GCC configuration is possible, including the GCC_KEYS register itself. SMU_GCC configuration is possible again after the PERLCK field of the GCC_KEYS register is reset to 0x00 by an application reset
In order to configure and lock the SMU_CS configuration the following steps shall be followed:
- The SMU_CS configuration is only possible if the CFGLCK field of the CS_KEYS register is set to 0xBC
- After SMU_CS configuration is done, CFGLCK field should be set to any other value beside 0xBC, for example 0x00, for locking the configuration
- If the PERLCK field of the CS_KEYS register is set to 0xFF no further SMU_CE configuration is possible, including the CS_KEYS register itself. SMU_CS configuration is possible again after the PERLCK field of the CS_KEYS register is reset to 0x00 by an application reset
Although CFGLCK field can be set to 0xBC during any SMU_CS state (with the exception of permanent lock using PERLCK=0xFF), it is recommended to configure and lock the SMU_CS configuration during START state.
- ReqIF-WF.Type: Requirement

###### PGBA-EHDA-AJIJ-IADI_test: Test
N.A.
- ReqIF-WF.Type: Requirement

###### PGBA-EHDA-AJIJ-IADI_reporting: Reporting
If the configuration registers are locked the write request will not update the registers. But no bus error or alarm will be triggered for this condition.
- ReqIF-WF.Type: Information

###### PGBA-EHDA-AJIJ-IADI_recommendederrorreaction: Recommended error reaction
N.A.
- ReqIF-WF.Type: Information

###### YKFA-EGFC-DDHB-AIDC: SM[HW]:SMU:REG_MONITOR
- IFX.Version: 21
- ReqIF-WF.Type: Heading

###### YKFA-EGFC-DDHB-AIDC_description: Description
The SMU implemented safety flip-flops for detecting transient faults in configuration registers and sequential logic. Safety flip-flops are special flip-flops that implement a hardware mechanism capable to detect bit flips within the flip-flops. The configuration and control registers which are designed with safety flip-flops are listed below. A single alarm, SMU_SAFE0/1 SMU_CS SFF Uncorrectable Error Alarm, is triggered from SMU_SAFE0, SMU_SAFE1 and SMU_CS upon the detection of uncorrectable errors within safety flip-flop and forwarded to SMU_STDBY. While in SMU_STDBY, an alarm SMU_STDBY SFF Uncorrectable Error Alarm is triggered upon the detection of uncorrectable errors within safety flip-flop and forwarded to SMU_SAFE0 and SMU_SAFE1.
The SMU_SAFE0 and SMU_SAFE1 configuration, control and status registers that shall be implemented with safety flip-flops are:
- SAFEx_CMD (where x = 0-1)
- SAFEx_AEX (where x = 0-1)
- SAFEx_FSPi_CON (where x = 0-1;i = 0-1)
- SAFEx_PES (where x = 0-1)
- SAFEx_AGC (where x = 0-1)
- SAFEx_RTC (where x = 0-1)
- SAFEx_RT0ACA (where x = 0-1)
- SAFEx_RT0ACB (where x = 0-1)
- SAFEx_RT1ACA (where x = 0-1)
- SAFEx_RT1ACB (where x = 0-1)
- SAFEx_AGSFi_CONj, SAFEx_AGSFi_CAS and SAFEx_AGSFi_FSPj (where x = 0-1; i = 0-13; j = 0-3)
- SAFEx_AGSHi_CONj, SAFEx_AGSHi_CAS and SAFEx_AGSHi_FSPj (where x = 0-1; i = 0-2; j = 0-3)
- SAFEx_PCTL (where x = 0-1)
- SAFEx_DBG (where x = 0-1)
The SMU_GCC configuration and control registers that shall be implemented with safety flip-flops are:
- GCC_EMSR
- GCC_ALMTST
- GCC_AGSHi_SEL (where i = 0-2)
The SMU_STDBY configuration and control registers that shall be implemented with safety flip-flops are:
- AGSTDBYi_FSPj (where i = 0-4; j = 0-3)
- MONBISTCTRL
- CMDSTDBY
The SMU_CS configuration and control registers that shall be implemented with safety flip-flops are:
- CS_CMD
- CS_AEX
- CS_RTC
- CS_RT0ACA
- CS_RT0ACB
- CS_AGCSi_CONj and CS_AGCSi_CAS (where i = 0-1; j = 0-2)
- CS_AGSHi_CONj and CS_AGSHi_CAS (where i = 0-2; j = 0-2)
- CS_ALMTST
- CS_DBG
- CS_AGSHi_SEL (where i = 0-2)
- ReqIF-WF.Type: Information

###### YKFA-EGFC-DDHB-AIDC_resetoperationalstate: Reset operational state
This safety mechanism is reset according to the
reset behavior of each of the registers above, as specified in the
Register Overview - SMU table in the User Manual.
- ReqIF-WF.Type: Information

###### YKFA-EGFC-DDHB-AIDC_configurationandactivation: Configuration and activation
N.A.
- ReqIF-WF.Type: Requirement

###### YKFA-EGFC-DDHB-AIDC_test: Test
The test procedure described below is not mandatory from safety point of view but can be useful for development purposes.
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
During the self-test the alarms listed in Reporting section are triggered in the SMU. After the completion of the test, it is required to clear these alarms in the SMU.
- ReqIF-WF.Type: Requirement

###### YKFA-EGFC-DDHB-AIDC_reporting: Reporting
Upon detection of an error, following alarms will be reported to the SMU.
- Fault reporting via SMU_SAFE0/1 SMU_CS SFF Uncorrectable Error Alarm to SMU_STDBY
- Fault reporting via SMU_STANDBY SFF Uncorrectable Error Alarm to SMU_SAFE0 and SMU_SAFE1.
- ReqIF-WF.Type: Information

###### YKFA-EGFC-DDHB-AIDC_recommendederrorreaction: Recommended error reaction
System integrator to select appropriate safe reaction in SMU.
- ReqIF-WF.Type: Information

###### NIMA-EHDG-JDHG-GGGC: SM[HW]:SMU:DIVERSE_REDUNDANCY
- IFX.Version: 1
- ReqIF-WF.Type: Heading

###### NIMA-EHDG-JDHG-GGGC_description: Description
The SMU provides redundant alarm handlers for diverse processing of alarms caused by common cause failure and certain critical alarms within the microcontroller. SMU_STDBY is implemented in stand-by domain and is supplied by back-up voltage and clocked by fBACK as compared to SMU_SAFEx (x=0,1) instances which are supplied with core voltage and clocked by fSPB. Common cause failure initiators can include voltage, clock, temperature monitors and failure of SMU_SAFEx (x=0,1). Moreover any incoming alarm to SMU_SAFEx (x=0,1) can be configured by application software to be considered as critical alarm (SM[HW]:SMU:CRITICAL_ALARM). If any of the mentioned alarms above is triggered, at least one of the alarm handlers (SMU_SAFEx (x=0,1) or SMU_STDBY ) shall be capable to trigger FAULT state indication on FSP pins to bring the system into safe state. The SMU chapter in user manual covers detailed description for SMU_SAFE0/SMU_SAFE1 as well as SMU_STDBY and the configuration required for the usage of FAULT state indication on FSP.
- ReqIF-WF.Type: Information

###### NIMA-EHDG-JDHG-GGGC_resetoperationalstate: Reset operational state
N.A.
- ReqIF-WF.Type: Information

###### NIMA-EHDG-JDHG-GGGC_configurationandactivation: Configuration and activation
N.A.
- ReqIF-WF.Type: Requirement

###### NIMA-EHDG-JDHG-GGGC_test: Test
N.A.
- ReqIF-WF.Type: Requirement

###### NIMA-EHDG-JDHG-GGGC_reporting: Reporting
N.A.
- ReqIF-WF.Type: Information

###### NIMA-EHDG-JDHG-GGGC_recommendederrorreaction: Recommended error reaction
N.A.
- ReqIF-WF.Type: Information

###### ZBTA-FJGE-IIIC-CCJC: SM[HW]:SMU:ENDINIT
- IFX.Version: 1
- ReqIF-WF.Type: Heading

###### ZBTA-FJGE-IIIC-CCJC_description: Description
The SMU provides a unique PROT mechanism (GCC_PROTGE, CS_PROTCE, SAFEx_PROTSE and PROTSTDBYE) that protects the configuration of the master agent function identifier based access protection (ACCEN) to support freedom from interference of different SW tasks.
On a detected violation the access is blocked.
GCC_PROTGE, CS_PROTCE, SAFEx_PROTSE: For the registers protected by GCC_PROTGE, CS_PROTCE and SAFEx_PROTSE see tables Register Overview – Access Mode Glossary and Register Overview – SMU (ascending Offset Address) in User Manual.
PROTSTDBYE: For the registers protected by PROTSTDBYE see tables Register Overview – Access Mode Glossary and Register Overview – SMU_STDBY (ascending Offset Address) in User Manual.
- ReqIF-WF.Type: Information

###### ZBTA-FJGE-IIIC-CCJC_resetoperationalstate: Reset operational state
The GCC_PROTGE, CS_PROTCE, SAFEx_PROTSE and PROTSTDBYE mechanisms are active after intentional configuration by application software.
- ReqIF-WF.Type: Information

###### ZBTA-FJGE-IIIC-CCJC_configurationandactivation: Configuration and activation
The GCC_PROTGE, CS_PROTCE, SAFEx_PROTSE and PROTSTDBYE mechanisms must be enabled and configured once via registers GCC_PROTGE, CS_PROTCE, SAFEx_PROTSE and PROTSTDBYE by application software. The alarm handling has to be configured in the SMU.
- ReqIF-WF.Type: Requirement

###### ZBTA-FJGE-IIIC-CCJC_test: Test
This safety measure can be tested after the PROT owner has been configured:
Write access to a protected register by a master agent function that is not the PROT owner.
- ReqIF-WF.Type: Requirement

###### ZBTA-FJGE-IIIC-CCJC_reporting: Reporting
On detection of an access protection violation the SMU will terminate the access with FPI error that is detected by the BCU, see SM[HW]:FPI:ERROR_HANDLING.
- ReqIF-WF.Type: Information

###### ZBTA-FJGE-IIIC-CCJC_recommendederrorreaction: Recommended error reaction
System integrator to select appropriate safe reaction in SMU.
- ReqIF-WF.Type: Information

###### FXNA-EHHJ-EIJB-EFAF: SM[HW]:SMU:SAFETY_ENDINIT
- IFX.Version: 10
- ReqIF-WF.Type: Heading

###### FXNA-EHHJ-EIJB-EFAF_description: Description
The SMU provides PROT mechanisms (GCC_PROTGSE, CS_PROTCSE, SAFEx_PROTSSE and PROTSTDBYSE) that protect the configuration of the master agent function identifier based access protection (ACCEN) to support freedom from interference of different SW tasks.
On a detected violation the access is blocked.
GCC_PROTGE, CS_PROTCE, SAFEx_PROTSE: For the registers protected by GCC_PROTGE, CS_PROTCE, SAFEx_PROTSE see tables Register Overview – Access Mode Glossary and Register Overview – SMU (ascending Offset Address) in User Manual.
PROTSTDBYSE: For the registers protected by PROTSTDBYSE see tables Register Overview – Access Mode Glossary and Register Overview – SMU_STDBY (ascending Offset Address) in User Manual.
- ReqIF-WF.Type: Information

###### FXNA-EHHJ-EIJB-EFAF_resetoperationalstate: Reset operational state
The GCC_PROTGSE, SAFEx_PROTSSE and PROTSTDBYSE mechanisms are active after intentional configuration by application software. The CS_PROTCSE mechanism is active after application reset.
- ReqIF-WF.Type: Information

###### FXNA-EHHJ-EIJB-EFAF_configurationandactivation: Configuration and activation
The GCC_PROTGSE, SAFEx_PROTSSE and PROTSTDBYSE mechanisms must be enabled and configured once via registers GCC_PROTGSE, SAFEx_PROTSSE and PROTSTDBYSE by application software. The alarm handling has to be configured in the SMU.
- ReqIF-WF.Type: Requirement

###### FXNA-EHHJ-EIJB-EFAF_test: Test
The test procedure described below is not mandatory from safety point of view but can be useful for development purposes.
This safety measure can be tested after the PROT owner has been configured:
Write access to a protected register by a master agent function that is not the PROT owner.
- ReqIF-WF.Type: Requirement

###### FXNA-EHHJ-EIJB-EFAF_reporting: Reporting
On detection of an access protection violation the SMU will terminate the access with FPI error that is detected by the BCU, see SM[HW]:FPI:ERROR_HANDLING.
- ReqIF-WF.Type: Information

###### FXNA-EHHJ-EIJB-EFAF_recommendederrorreaction: Recommended error reaction
System integrator to select appropriate safe reaction in SMU.
- ReqIF-WF.Type: Information

###### WZLA-EHHJ-EIJB-BBCC: SM[HW]:SMU:SV_AP
- IFX.Version: 1
- ReqIF-WF.Type: Heading

###### WZLA-EHHJ-EIJB-BBCC_description: Description
Critical module registers are implemented with a write access restriction that restricts the write access to access with supervisor (SV) privilege.
On a detected violation the access is blocked.
For the registers protected by SV see tables Register Overview – Access Mode Glossary and Register Overview – SMU (ascending Offset Address) in User Manual.
- ReqIF-WF.Type: Information

###### WZLA-EHHJ-EIJB-BBCC_resetoperationalstate: Reset operational state
The safety mechanism is active after application reset.
- ReqIF-WF.Type: Information

###### WZLA-EHHJ-EIJB-BBCC_configurationandactivation: Configuration and activation
The alarm handling has to be configured in the SMU.
- ReqIF-WF.Type: Requirement

###### WZLA-EHHJ-EIJB-BBCC_test: Test
This safety measure can be tested by a write access to a protected register by a master agent function without Supervisor (SV) access rights.
- ReqIF-WF.Type: Requirement

###### WZLA-EHHJ-EIJB-BBCC_reporting: Reporting
On detection of an access protection violation the SMU will terminate the access with FPI error that is detected by the BCU, see SM[HW]:FPI:ERROR_HANDLING.
- ReqIF-WF.Type: Information

###### WZLA-EHHJ-EIJB-BBCC_recommendederrorreaction: Recommended error reaction
System integrator to select appropriate safe reaction in SMU.
- ReqIF-WF.Type: Information

###### DLUA-EHHJ-EIJB-EJCJ: SM[HW]:SMU:CFG_AS_AP
- IFX.Version: 9
- ReqIF-WF.Type: Heading

###### DLUA-EHHJ-EIJB-EJCJ_description: Description
The SMU checks if the access master agent function identifier is enabled for the type of access (read access and write access, configured through the SMU ACCEN registers) to the selected register.
On a detected violation the access is blocked.
- ReqIF-WF.Type: Information

###### DLUA-EHHJ-EIJB-EJCJ_resetoperationalstate: Reset operational state
The safety mechanism is inactive after application reset.
- ReqIF-WF.Type: Information

###### DLUA-EHHJ-EIJB-EJCJ_configurationandactivation: Configuration and activation
The ACCEN mechanism must be enabled and configured once via registers ACCENx by application software. The alarm handling has to be configured in the SMU.
- ReqIF-WF.Type: Requirement

###### DLUA-EHHJ-EIJB-EJCJ_test: Test
The test procedure described below is not mandatory from safety point of view but can be useful for development purposes.
This safety measure can be tested after the ACCENx has been configured:
Write access to a protected register by a master agent function that is not the ACCEN owner.
- ReqIF-WF.Type: Requirement

###### DLUA-EHHJ-EIJB-EJCJ_reporting: Reporting
On detection of an access protection violation the SMU terminate the access with FPI error that is detected by the BCU, see SM[HW]:FPI:ERROR_HANDLING.
- ReqIF-WF.Type: Information

###### DLUA-EHHJ-EIJB-EJCJ_recommendederrorreaction: Recommended error reaction
System integrator to select appropriate safe reaction in SMU.
- ReqIF-WF.Type: Information

##### HZBA-EHBA-BEAI-FDBA: Alarms
SMU alarms
| Alarm name | Safety mechanism | Alarm flag to be cleared in |
| --- | --- | --- |
| SMU_SAFE0 Alive Alarm | SM[HW]:SMU:ALIVE_MONITOR | SMU only |
| SMU_SAFE1 Alive Alarm | SM[HW]:SMU:ALIVE_MONITOR | SMU only |
| SMU_CS Alive Alarm | SM[HW]:SMU:ALIVE_MONITOR | SMU only |
| SMU_SAFE0 FSP0 Fault State Activation Alarm | SM[HW]:SMU:FSP_MONITOR | SMU only |
| SMU_SAFE0 FSP1 Fault State Activation Alarm | SM[HW]:SMU:FSP_MONITOR | SMU only |
| SMU_SAFE1 FSP2 Fault State Activation Alarm | SM[HW]:SMU:FSP_MONITOR | SMU only |
| SMU_SAFE1 FSP3 Fault State Activation Alarm | SM[HW]:SMU:FSP_MONITOR | SMU only |
| SMU_SAFE0 Critical Alarm | SM[HW]:SMU:CRITICAL_ALARM | SMU only |
| SMU_SAFE1 Critical Alarm | SM[HW]:SMU:CRITICAL_ALARM | SMU only |
| SMU_CS Critical Alarm | SM[HW]:SMU:CRITICAL_ALARM | SMU only |
| SMU_SAFE0 RT0 Time-out Alarm | SM[HW]:SMU:RT | SMU only |
| SMU_SAFE0 RT1 Time-out Alarm | SM[HW]:SMU:RT | SMU only |
| SMU_SAFE1 RT0 Time-out Alarm | SM[HW]:SMU:RT | SMU only |
| SMU_SAFE1 RT1 Time-out Alarm | SM[HW]:SMU:RT | SMU only |
| SMU_CS RT0 Time-out Alarm | SM[HW]:SMU:RT | SMU only |
| SMU_SAFE0/1 SMU_CS SFF Uncorrectable Error Alarm | SM[HW]:SMU:REG_MONITOR | SMU only |
| SMU_STANDBY SFF Uncorrectable Error Alarm | SM[HW]:SMU:REG_MONITOR | SMU only |
| FPI error alarm | SM[HW]:SMU:SV_AP SM[HW]:SMU:CFG_AS_AP SM[HW]:SMU:ENDINIT SM[HW]:SMU:SAFETY_ENDINIT | SMU only |
- IFX.Version: 1
- ReqIF-WF.Type: Information

##### OOFA-FAFF-IJHG-EIFJ: External safety mechanisms
- IFX.Version: 1
- ReqIF-WF.Type: Information

###### HGYA-EHHE-ICEB-BCAG: ESM[SW]:SMU:CONFIG_READBACK
- IFX.Version: 5
- ReqIF-WF.Type: Heading

###### HGYA-EHHE-ICEB-BCAG_description: Description
The SMU configuration and status clearing registers have to be read back after write. The read back values have to be compared with the written values. In case of any difference the [Application Software] shall trigger a reaction.
The read back after write is required for all of the registers described in the SMU chapter of user manual. The only exceptions are read only registers (as indicated by BE in access mode write field in the register overview SMU and SMU_STDBY tables in the user manual) where anyway write requests to those registers are not possible.
- ReqIF-WF.Type: Requirement

###### NUAA-EHDG-JHHJ-FJIJ: ESM[SW]:SMU:STDBY_MONBIST
- IFX.Version: 7
- ReqIF-WF.Type: Heading

###### NUAA-EHDG-JHHJ-FJIJ_description: Description
The SMU_STDBY contains a built-in mechanism that allows users to test alarm paths, alarm configurations, and alarm reactions. The MONBISTCTRL register allows the user to start the BIST of the SMU_STDBY. Results of the BIST are available in the MONBISTSTAT register. For a detailed description of MONBIST execution refer to the Power Management Unit Chapter section "Standby SMU Integration and Monitor BIST (MONBIST)".
- ReqIF-WF.Type: Requirement

###### POFA-FAGB-GIAJ-FDIB: ESM[SW]:SMU:ALARM_SIGNAL_TEST
The toggling of alarm status bitfields from 0 then 1 and again 0 in corresponding step 2, 5 and 9 indicates non existence of any fault in the signals. The presence of stuck-at fault can be detected if the same value appears on alarm status bitfields in step 2, 5 and 9. The whole steps for the test are also summarized in figure below.
Alarm signal test: Steps overview
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Only one SMU_SAFE instance for example SMU_SAFE0 can be used during the test. But it is important to clear the alarm status bitfields in other instance for example SMU_SAFE1 at the end of the test.
Similar test capability is also provided in SMU_CS for testing security alarms independently where bitfield CS_ALMTST.TE is used to drive global test signal ALMCS_T and alarm status bitfields CS_AGCSi_STS.SFj can be used to test alarm ALMCSi[j]. All the security alarm signals where the test can be performed are listed in the product specific Alarm Mapping Tables in the user manual.
- IFX.Version: 1
- ReqIF-WF.Type: Heading

###### POFA-FAGB-GIAJ-FDIB_description: Description
The SMU_GCC along with SMU_SAFE0 or SMU_SAFE1 provides the capability to detect stuck-at faults on alarm signal lines. The test shall be performed during startup where SMU_SAFE0 or SMU_SAFE1 shall be in Start state and no alarm can be processed. This test shall be executed at least once per driving cycle.
All the alarm signals where the test can be performed are listed in the product specific Alarm Mapping Tables in the user manual. Although the test procedure remains the same for all listed alarm signals, but for simplicity the test procedure is explained below with an example of two alarm signals ALMSFi[j] and ALMSFm[n] as shown in the Figure 1.
Alarm signal test
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Following steps are required to detect stuck-at faults on alarm signal:
1. Clear alarm status bitfields SAFEx_AGSFi_STS.SFj and SAFEx_AGSFm_STS.SFn as described in SMU chapter (Alarm Status Registers section) of user manual
2. Read alarm status bitfields SAFEx_AGSFi_STS.SFj and SAFEx_AGSFm_STS.SFn. It is expected that the corresponding bitfields are set to 0
3. Set GCC_ALMTST.TE = 1. This will set ALMSF_T signal to 1
4. Wait for few f SPB clock cycles, for example 8 clock cycles, so that ALMSF_T signal propagates to all corresponding functional blocks
5. Read alarm status bitfields SAFEx_AGSFi_STS.SFj and SAFEx_AGSFm_STS.SFn. It is expected that the corresponding bitfields are set to 1
6. Set GCC_ALMTST.TE = 0. This will set ALMSF_T signal to 0
7. Wait for few f SPB clock cycles, for example 8 clock cycles, so that ALMSF_T signal propagates to all corresponding functional blocks
8. Clear alarm status bitfields SAFEx_AGSFi_STS.SFj and SAFEx_AGSFm_STS.SFn as described in SMU chapter (Alarm Status Registers section) of user manual
9. Read alarm status bitfields SAFEx_AGSFi_STS.SFj and SAFEx_AGSFm_STS.SFn. It is expected that the corresponding bitfields are set to 0
- ReqIF-WF.Type: Requirement

###### ZGPA-FJCA-ABJA-IGJC: ESM[HW]:SYS:FSP_ERROR_PIN_MONITOR
- IFX.Version: 9
- ReqIF-WF.Type: Heading

###### ZGPA-FJCA-ABJA-IGJC_description: Description
A component independent from the AURIX™ microcontroller shall monitor the FSP ErrorPins FSP[0:3] that are used by a safety relevant application. Monitoring of unused FSP pins is not required.
The FSP ErrorPins provide a fast and software independent information about the presence of an internal failure of the microcontroller which is reported to SMU as an alarm. As an alarm action, the error reporting with FSP ErrorPins FSP[0:3] can be combined with an internal reaction such as NMI[0:3] or IRQ[0:5] by configuring SMU_SAFE0 and SMU_SAFE1.
A violation of a Safety Goal may happen due to hardware faults of the microcontroller's infrastructure related functional blocks including Clocking and PMS which effects the SMU functionality. In case the SMU_STDBY is not used to control ErrorPins (FSP[0:3]) to react on alarm from infrastructure monitors, the application software shall implement SMU status checks. In this case, upon appearance of an infrastructure faults, the system integrator is responsible to decide on the appropriate action. The list below provides some recommendation
1. SMU_STDBY hardware alarm path described in SM[HW]:SMU:ALIVE_MONITOR can be replaced by:
1. Software cyclic reads within FTTI of either:
- AGSTDBYi_STS registers (refer to alarm mapping for ALMSTDBY4[2] and ALMSTDBY4[3], or
- SAFEx_AGSFi_STS and SAFEx_AGSHi_STS registers and plausibility check in software if the configured error reaction (for example ErrorPin) was executed as expected
2. And triggering software alarms in parallel by SMU_SAFE commands and ESM[HW]:SYS:WATCHDOG_FUNCTION in case the software execution is not reliable due to infrastructure failure
2. SMU_STDBY hardware alarm path described in PMS safety mechanism can be replaced by
1. Software cyclic reads of AGSTDBYi_STS registers (refer to alarm mapping for corresponding alarms)
2. And triggering software alarms in parallel by SMU_SAFE commands and ESM[HW]:SYS:WATCHDOG_FUNCTION in case the software execution is not reliable due to infrastructure failure
3. SMU_STDBY hardware alarm path described in SM[HW]:CLOCK:ALIVE_MONITOR, SM[HW]:CLOCK:PLL_LCKSTP_MONITOR and SM[HW]:CLOCK:DIV_LCKSTP_MONITOR can be replaced by:
- Application SW has to detect wrong peripheral operation (in case of fPLL1, fPLL2 failure) and ESM[HW]:SYS:WATCHDOG_FUNCTION (in case of fPLL0 failure)
4. In case SMU_SAFE0 and SMU_SAFE1 is configured to trigger FAULT state on FSP ErrorPins as an reaction to a alarm, correct activation can be checked by software cyclic reads of FSP ErrorPins status bits (refer to the register SAFEx_STS)
- ReqIF-WF.Type: Information

#### SKSA-EICE-HIFI-FIHB: Signal Processing Unit (SPU)
- IFX.Version: 1
- ReqIF-WF.Type: Information

##### ODGA-FAFF-IADC-CGCB: Internal safety mechanisms
- IFX.Version: 1
- ReqIF-WF.Type: Information

###### CZMA-FBDI-GAGB-CIHH: SM[HW]:SPU:CFG_AS_AP
- IFX.Version: 1
- ReqIF-WF.Type: Heading

###### CZMA-FBDI-GAGB-CIHH_description: Description
The SPU provides a unique master agent function identifier based access protection mechanism (APU) that protects the configuration of the SPU registers.
The SPU checks if the access master agent function identifier is enabled for the type of access (read access and write access, configured through the SPU ACCEN registers) to the selected register.
Unauthorized access attempts are blocked by this mechanism.
- ReqIF-WF.Type: Information

###### CZMA-FBDI-GAGB-CIHH_resetoperationalstate: Reset operational state
An application reset will set the configuration of this safety mechanism back to its default value.
- ReqIF-WF.Type: Information

###### CZMA-FBDI-GAGB-CIHH_configurationandactivation: Configuration and activation
This safety mechanism is active after intentional configuration by application software through the ACCENx registers.
- ReqIF-WF.Type: Requirement

###### CZMA-FBDI-GAGB-CIHH_test: Test
This safety measure can be tested after the SPU ACCEN registers have been configured using an access to a protected register by a master agent function that is not enabled for the type of access configured by the RDMA ACCEN registers.
- ReqIF-WF.Type: Requirement

###### CZMA-FBDI-GAGB-CIHH_reporting: Reporting
On detection of an access protection violation the SPU will terminate the access with an FPI error that is detected by the BCU, see SM[HW]:FPI:ERROR_HANDLING.
- ReqIF-WF.Type: Information

###### CZMA-FBDI-GAGB-CIHH_recommendederrorreaction: Recommended error reaction
System integrator to select an appropriate safe reaction in the SMU.
- ReqIF-WF.Type: Information

###### NCGA-FBDI-GBAF-ADFF: SM[HW]:SPU:ACTIVE_CONFIG_CHECK
- IFX.Version: 7
- ReqIF-WF.Type: Heading

###### NCGA-FBDI-GBAF-ADFF_description: Description
The SPU uses checksums to protect configuration and parameter data. A checksum is a cyclic redundancy checksum (CRC) calculated over the SPU protected data. There are two types of protected data: register configurations and parameter vectors. The parameter vectors are accessed by software in the configuration memory.
The SPU periodically calculates a SPU checksum over each set of data. On completion of the calculation, the SPU compares the calculated checksum with an expected SPU checksum. For register configurations the expected checksum is stored in REGCRC.CRC. For parameter vectors the expected checksum is stored after the end of each parameter vector. If the calculated and expected SPU checksums do not match, the SPU triggers an alarm.
The CRC calculation uses the CRC-32 Ethernet polynomial as defined in the IEEE 802.3 standard which assumes that the data are converted to an LSB first sequential data stream. For the register configuration check the data stream is generated using the defined registers from ID_CONF to CTRL inclusive, skipping any unused register addresses. Additionally, the value of following registers and bit-fields should be assumed to be 0 H for calculating the reference CRC.
- All reserved bit-fields
- All write-only bit-fields
- PACTR.COUNT
- CBTDSTAT
- TRGCNT_IDMA.CNT
- TRGCNT_IDMB.CNT
- TRGCNT_ODM.CNT
- CTRL.TRIG
- CTRL.BUSY
- CTRL.NXT_CONF
- REGCRC
For the parameter vector check the data stream is generated using the whole of the parameter vector data. The parameter check is done on the data pointed to by the following configuration memory base address registers, each of which has its own expected CRC:
- FILTCB: the MATH0 filter coefficients
- ZICB: the MATH1 zero insertion mask
- BINREJB: the MATH2 bin rejection mask
The calculation of the CRC takes one fSRI clock cycle per 32-bit register or value. The comparison takes two fSRI clock cycles. The parameter data sets are processed in parallel with the register data and, as the number of registers is greater than the longest parameter data set, the overall processing time is determined by the number of registers covered by the mechanism.
Note: If the SPU configuration is such that the number of clock cycles taken to complete a data processing operation is less than the number of clock cycles taken to calculate the register checksum and compare with the expected checksum then no alarm will be triggered. Given the SPU is intended to be used to process radar data cubes consisting of at least 256 elements the check will normally be completed at least once.
- ReqIF-WF.Type: Information

###### NCGA-FBDI-GBAF-ADFF_resetoperationalstate: Reset operational state
This safety mechanism is reset and disabled by module reset.
- ReqIF-WF.Type: Information

###### NCGA-FBDI-GBAF-ADFF_configurationandactivation: Configuration and activation
The SPU configuration checksum is enabled by writing 10 B to the SM_CTRL.REGCRCEN bit-field and disabled by writing 01 B. The register checksum calculation and check are only done when the SPU is not in the IDLE state as indicated by the CTRL.BUSY register bit.. In addition, each parameter checksum is only enabled when the function that uses the parameter vector is enabled.
Before triggering the SPU the application software shall write a valid CRC to REGCRC.CRC that is calculated by processing a memory image of the registers as described above, not by reading the registers. Alternatively, where the configuration is stored in the SPU configuration memory (CMEM), the value shall be written to the appropriate location in configuration data set. For each enabled function that uses a parameter data vector the application software shall write a valid CRC at the end of the vector in the CMEM.
- ReqIF-WF.Type: Requirement

###### NCGA-FBDI-GBAF-ADFF_test: Test
The state machine of this safety mechanism is checked by SM[HW]:SPU:ACTIVE_CONFIG_CHECK_SCC. The application software shall test the alarm path of this safety mechanism at least once per Multi-Point Fault Detection Time Interval (MPFDTI) which can be done by writing an invalid CRC to REGCRC.CRC or by writing an invalid CRC after the end of a parameter vector for an enabled function that uses the vector.
- ReqIF-WF.Type: Requirement

###### NCGA-FBDI-GBAF-ADFF_reporting: Reporting
If the SPU checksum comparison fails, the SPU generates an SPU alarm.
- ReqIF-WF.Type: Information

###### NCGA-FBDI-GBAF-ADFF_recommendederrorreaction: Recommended error reaction
System integrator to select appropriate safe reaction in SMU.
- ReqIF-WF.Type: Information

###### YMEA-FCAJ-JCJJ-DFGJ: SM[HW]:SPU:ACTIVE_CONFIG_CHECK_SCC
- IFX.Version: 1
- ReqIF-WF.Type: Heading

###### YMEA-FCAJ-JCJJ-DFGJ_description: Description
The active configuration check has to sequence through states to read each configuration register and then compare the resulting CRC over the registers with the expected value. This sequential logic is duplicated and its state compared with the state in the duplicate . A fault is detected when the state differs.
- ReqIF-WF.Type: Information

###### YMEA-FCAJ-JCJJ-DFGJ_resetoperationalstate: Reset operational state
This safety mechanism is enabled after application reset.
- ReqIF-WF.Type: Information

###### YMEA-FCAJ-JCJJ-DFGJ_configurationandactivation: Configuration and activation
N.A.
- ReqIF-WF.Type: Requirement

###### YMEA-FCAJ-JCJJ-DFGJ_test: Test
N.A.
- ReqIF-WF.Type: Requirement

###### YMEA-FCAJ-JCJJ-DFGJ_reporting: Reporting
If this safety mechanism detects a fault, the SM_STAT.SMCLSTS bit is set. No alarm is triggered.
- ReqIF-WF.Type: Information

###### YMEA-FCAJ-JCJJ-DFGJ_reaction: Reaction
System integrator to select appropriate safe reaction in SMU.
- ReqIF-WF.Type: Information

###### GRGA-FBDI-GDFB-AJJC: SM[HW]:SPU:SEP_TRANSACTION_INTEGRITY
- IFX.Version: 9
- ReqIF-WF.Type: Heading

###### GRGA-FBDI-GDFB-AJJC_description: Description
The SEP interface implements redundancy and EDC mechanisms to ensure transaction integrity.
- All request, acknowledge and error signals are redundantly encoded with an inverted parity. The RMEM design part generates an alarm if it detects a parity error on the request signals. The SPU generates an alarm if it detects a parity error on the acknowledge or error signals
- On read accesses, the RMEM design part generates an EDC covering the read address and data. The generated EDC is transmitted to the SPU along with the read address and data. The SPU performs an EDC check on the received read address and data and generates an alarm if the check fails
- On write accesses, the SPU generates an EDC covering the write address and data. The generated EDC is transmitted to the RMEM design part along with the write address and data. The RMEM design part performs an EDC check on the received write address and data and generates an alarm if the check fails
- ReqIF-WF.Type: Information

###### GRGA-FBDI-GDFB-AJJC_resetoperationalstate: Reset operational state
This safety mechanism is enabled and active after module reset.
- ReqIF-WF.Type: Information

###### GRGA-FBDI-GDFB-AJJC_configurationandactivation: Configuration and activation
N.A.
- ReqIF-WF.Type: Requirement

###### GRGA-FBDI-GDFB-AJJC_test: Test
This safety mechanism shall be tested at least once per Multi-Point Fault Detection Time Interval (MPFDTI) by:
- Setting bit-field SM_USER.RMRCTST to ON and executing an operation which results in the SPU generating a request to the RMEM. The SPU inserts a parity error on the request signals to the RMEM, which in turn results in the RMEM generating an SEP transaction integrity alarm
- Setting SPU bit-field SM_USER.RDECCTST to ON and executing an operation which results in the SPU generating a read request to the RMEM. The SPU inserts a EDC error on the read response to the SPU, which in turn results in the SPU generating an SEP transaction integrity alarm
- Setting bit-field SM_USER.RMCTST to ON. The SPU injects an error into the mechanism checking the signals from the RMEM, which in turn results in the SPU generating an SEP transaction integrity alarm
A read request from the SPU to the RMEM will occur when the SPU is configured to read data from RMEM by setting ID_CONF2.SRC=RM and triggering the SPU by setting CTRL.MODE=SW and CTRL.TRIG=1 B.
- ReqIF-WF.Type: Requirement

###### GRGA-FBDI-GDFB-AJJC_reporting: Reporting
On
detection of a parity or EDC violation by RMEM, the RMEM SEP error
alarm is raised. If the error is detected by the SPU, then the SPU
alarm is raised.
- ReqIF-WF.Type: Information

###### GRGA-FBDI-GDFB-AJJC_recommendederrorreaction: Recommended error reaction
System integrator to select appropriate safe reaction in SMU.
- ReqIF-WF.Type: Information

###### YYGA-FBDI-GBAH-GEHC: SM[HW]:SPU:DATA_PROTECTION
- IFX.Version: 2
- ReqIF-WF.Type: Heading

###### YYGA-FBDI-GBAH-GEHC_description: Description
The SPU implements EDC mechanisms to ensure data integrity within the SPU.
All data are redundantly encoded with an EDC if they are to be stored in registers and the EDC is checked before using the data. The SPU generates an alarm if it detects an EDC error .
- ReqIF-WF.Type: Information

###### YYGA-FBDI-GBAH-GEHC_resetoperationalstate: Reset operational state
This safety mechanism is enabled and active after module reset.
- ReqIF-WF.Type: Information

###### YYGA-FBDI-GBAH-GEHC_configurationandactivation: Configuration and activation
Not applicable.
- ReqIF-WF.Type: Requirement

###### YYGA-FBDI-GBAH-GEHC_test: Test
This safety mechanism can be tested by... TBD
- ReqIF-WF.Type: Requirement

###### YYGA-FBDI-GBAH-GEHC_reporting: Reporting
On detection of a EDC violation the SPU generates an SPU data protection alarm.
- ReqIF-WF.Type: Information

###### YYGA-FBDI-GBAH-GEHC_recommendederrorreaction: Recommended error reaction
System integrator to select appropriate safe reaction in SMU.
- ReqIF-WF.Type: Information

###### EZEA-FBDI-GBBA-IGFJ: SM[HW]:SPU:CONTROL_FLOW_SIGNATURE
- IFX.Version: 6
- ReqIF-WF.Type: Heading

###### EZEA-FBDI-GBBA-IGFJ_description: Description
The SPU implements CRC calculations on key internal interfaces. These include but are not limited to:
- Internal SRAM interfaces of the FFT accelerator
- Interfaces to buffer memories
- Input data manager (IDM) RMEM interface
- Output data manager (ODM) RMEM interface
- Configuration memory interfaces
These CRCs are separated into two groups:
- CRCs which are independent of the data being processed
- CRCs which are dependent on the data being processed
When the SPU has finished processing, as indicated by CTRL.BUSY==DONE or an End of linked list interrupt, each group of CRCs are aggregated by calculating a single CRC result over the whole group. The two aggregate CRC values are accessible in the register space of the SPU as CRC_CTRL_CRC, data independent, and CRC_DATA_CRC, data dependent. The data independent CRC is called the control CRC while the data dependent one is called the data CRC.
- ReqIF-WF.Type: Information

###### EZEA-FBDI-GBBA-IGFJ_resetoperationalstate: Reset operational state
This safety mechanism is disabled after module reset.
- ReqIF-WF.Type: Information

###### EZEA-FBDI-GBBA-IGFJ_configurationandactivation: Configuration and activation
N.A.
- ReqIF-WF.Type: Requirement

###### EZEA-FBDI-GBBA-IGFJ_test: Test
N.A.
- ReqIF-WF.Type: Requirement

###### EZEA-FBDI-GBBA-IGFJ_reporting: Reporting
N.A.
- ReqIF-WF.Type: Information

###### EZEA-FBDI-GBBA-IGFJ_recommendederrorreaction: Recommended error reaction
N.A.
- ReqIF-WF.Type: Information

###### VFUA-FBDI-GBBG-JCAF: SM[HW]:SPU:TRIGGER_PARITY
- IFX.Version: 1
- ReqIF-WF.Type: Heading

###### VFUA-FBDI-GBBG-JCAF_description: Description
The RDMA and RIF implement the SPU triggers and acknowledge triggers using a redundant encoding using an inverted parity. The SPU checks the parity of the received trigger from the RDMA and RIF and raises an alarm on detection of a parity mismatch.
- ReqIF-WF.Type: Information

###### VFUA-FBDI-GBBG-JCAF_resetoperationalstate: Reset operational state
This safety mechanism is enabled and active after module reset.
- ReqIF-WF.Type: Information

###### VFUA-FBDI-GBBG-JCAF_configurationandactivation: Configuration and activation
Not applicable.
- ReqIF-WF.Type: Requirement

###### VFUA-FBDI-GBBG-JCAF_test: Test
This safety mechanism can be tested by setting bit-field CHc_CTRL_SMUSER.TRGPTST to ON in the RDMA and executing an operation which results in the RDMA generating an acknowledge trigger to the SPU. TBC: do we need the same from RIF?
- ReqIF-WF.Type: Requirement

###### VFUA-FBDI-GBBG-JCAF_reporting: Reporting
When the SPU detects incorrect parity on the trigger from RIF or acknowledge trigger input from the RDMA, it generates an SPU trigger parity alarm.
- ReqIF-WF.Type: Information

###### VFUA-FBDI-GBBG-JCAF_recommendederrorreaction: Recommended error reaction
System integrator to select appropriate safe reaction in SMU.
- ReqIF-WF.Type: Information

###### QJKA-FBDI-GBCA-HAIJ: SM[HW]:SPU:RIF_INTERFACE
- IFX.Version: 1
- ReqIF-WF.Type: Heading

###### QJKA-FBDI-GBCA-HAIJ_description: Description
The data path between RIF and SPU is protected by a CRC. The CRC is calculated by the RIF over all the samples in each ramp and appended to the sample data. The number of samples in a ramp is determined from the value in the ID_CONF.SMPLCNT bit-field. The SPU calculates a CRC over the data as it is written into the internal assembly buffer of the IDM. The SPU raises an alarm on detection of a mismatch between the calculated and received CRCs.
- ReqIF-WF.Type: Information

###### QJKA-FBDI-GBCA-HAIJ_resetoperationalstate: Reset operational state
An application reset will disable this safety mechanism.
- ReqIF-WF.Type: Information

###### QJKA-FBDI-GBCA-HAIJ_configurationandactivation: Configuration and activation
This safety mechanism is enabled by writing 10 B to the SM_CTRL.RIFCRC bit-field.
- ReqIF-WF.Type: Requirement

###### QJKA-FBDI-GBCA-HAIJ_test: Test
This safety mechanism can be tested by writing 10 B to the SM_USER.RCRCTST bit-field .
- ReqIF-WF.Type: Requirement

###### QJKA-FBDI-GBCA-HAIJ_reporting: Reporting
On detection of a CRC error the SPU generates an SPU RIF interface alarm.
- ReqIF-WF.Type: Information

###### QJKA-FBDI-GBCA-HAIJ_recommendederrorreaction: Recommended error reaction
System integrator to select an appropriate safe reaction in the SMU.
- ReqIF-WF.Type: Information

###### JMMA-FBDI-GBEA-ADDF: SM[HW]:SPU:CONTROL_REDUNDANCY
- IFX.Version: 1
- ReqIF-WF.Type: Heading

###### JMMA-FBDI-GBEA-ADDF_description: Description
The control redundancy detects permanent and transient faults in the operation of a hardware element. Two symmetrical hardware modules perform duplicate operations and the results are compared. Any mismatch results in an error condition.
A hardware based self-test detects latent faults in the control redundancy mechanism and a software based test detects latent faults in the alarm.
The SPU uses control redundancy to cover the logic that is not covered by SM[HW]:SPU:ACTIVE_CFG_CHECK, SM[HW]:SPU:TRIGGER_PARITY or SM[HW]:SPU:SEP_TRANSACTION_INTEGRITY.
- ReqIF-WF.Type: Information

###### JMMA-FBDI-GBEA-ADDF_resetoperationalstate: Reset operational state
This safety mechanism is enabled after application reset.
- ReqIF-WF.Type: Information

###### JMMA-FBDI-GBEA-ADDF_configurationandactivation: Configuration and activation
N.A.
- ReqIF-WF.Type: Requirement

###### JMMA-FBDI-GBEA-ADDF_test: Test
The control redundancy compare function provides the application software with the ability to generate an alarm by setting the redundantly encoded SM_CTRL.xRTST = ON. This will inject an error into the comparators until it is set to OFF.
The following faults will be detected:
- A stuck at fault on the alarm signal path
- ReqIF-WF.Type: Requirement

###### JMMA-FBDI-GBEA-ADDF_reporting: Reporting
If this safety mechanism detects a fault, the SPU generates a SPU control redundancy mismatch alarm.
- ReqIF-WF.Type: Information

###### JMMA-FBDI-GBEA-ADDF_recommendederrorreaction: Recommended error reaction
System integrator to select appropriate safe reaction in SMU.
- ReqIF-WF.Type: Information

###### MMVA-FBDI-GBCF-JIEB: SM[HW]:SPU:SV_AP
- IFX.Version: 3
- ReqIF-WF.Type: Heading

###### MMVA-FBDI-GBCF-JIEB_description: Description
Critical module registers are implemented with a write access restriction that allows access only to masters with supervisor (SV) mode privilege.
Unauthorized access attempts are blocked by this mechanism.
For a list of the registers protected by SV, see tables Register overview – access mode glossary and Register overview – SPU (ascending offset address) in the User Manual.
- ReqIF-WF.Type: Information

###### MMVA-FBDI-GBCF-JIEB_resetoperationalstate: Reset operational state
The safety mechanism is active after application reset.
- ReqIF-WF.Type: Information

###### MMVA-FBDI-GBCF-JIEB_configurationandactivation: Configuration and activation
N.A.
- ReqIF-WF.Type: Requirement

###### MMVA-FBDI-GBCF-JIEB_test: Test
This safety measure can be tested by an write access to a protected register by a master agent function without supervisor (SV) access rights.
- ReqIF-WF.Type: Requirement

###### MMVA-FBDI-GBCF-JIEB_reporting: Reporting
On detection of an access protection violation the SPU will terminate the access with an FPI error that is detected by the BCU, see SM[HW]:FPI:ERROR_HANDLING.
- ReqIF-WF.Type: Information

###### MMVA-FBDI-GBCF-JIEB_recommendederrorreaction: Recommended error reaction
System integrator to select an appropriate safe reaction in the SMU.
- ReqIF-WF.Type: Information

###### IVMA-FBDI-GBDC-GCHD: SM[HW]:SPU:ENDINIT
- IFX.Version: 3
- ReqIF-WF.Type: Heading

###### IVMA-FBDI-GBDC-GCHD_description: Description
The SPU provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – SPU (ascending offset address) in the User Manual.
- ReqIF-WF.Type: Information

###### IVMA-FBDI-GBDC-GCHD_resetoperationalstate: Reset operational state
An application reset will set the configuration of this safety mechanism back to its default value.
- ReqIF-WF.Type: Information

###### IVMA-FBDI-GBDC-GCHD_configurationandactivation: Configuration and activation
This safety mechanism is active after intentional configuration by application software through the PROTE register.
- ReqIF-WF.Type: Requirement

###### IVMA-FBDI-GBDC-GCHD_test: Test
This safety measure can be tested after the PROT owner has been configured: Write access to a protected register by a master agent function that is not the PROT owner.
- ReqIF-WF.Type: Requirement

###### IVMA-FBDI-GBDC-GCHD_reporting: Reporting
On detection of an access protection violation the SPU will terminate the access with FPI error that is detected by the BCU, see SM[HW]:FPI:ERROR_HANDLING.
- ReqIF-WF.Type: Information

###### IVMA-FBDI-GBDC-GCHD_recommendederrorreaction: Recommended error reaction
System integrator to select an appropriate safe reaction in the SMU.
- ReqIF-WF.Type: Information

###### ILAA-FBDI-GBDF-BBJJ: SM[HW]:SPU:SAFETY_ENDINIT
- IFX.Version: 3
- ReqIF-WF.Type: Heading

###### ILAA-FBDI-GBDF-BBJJ_description: Description
The SPU provides a PROT mechanisms (PROTSE) that protect the configuration of critical registers. The ACCEN mechanism is based on the master agent function identifier.
The PROT mechanism supports freedom from interference of different SW tasks. Unauthorized access attempts are blocked by these mechanisms.
For a list of the registers protected by PROTSE, see tables Register overview – access mode glossary and Register overview – SPU (ascending offset address) in the User Manual.
- ReqIF-WF.Type: Information

###### ILAA-FBDI-GBDF-BBJJ_resetoperationalstate: Reset operational state
An application reset will set the configuration of this safety mechanism back to its default value.
- ReqIF-WF.Type: Information

###### ILAA-FBDI-GBDF-BBJJ_configurationandactivation: Configuration and activation
This safety mechanism is active after intentional configuration by application software through the PROTSE registers.
- ReqIF-WF.Type: Requirement

###### ILAA-FBDI-GBDF-BBJJ_test: Test
This safety measure can be tested after the PROT owner has been configured using a write access to a protected register by a master agent function that is not the PROT owner.
- ReqIF-WF.Type: Requirement

###### ILAA-FBDI-GBDF-BBJJ_reporting: Reporting
On detection of an access protection violation the SPU will terminate the access with an FPI error that is detected by the BCU, see SM[HW]:FPI:ERROR_HANDLING.
- ReqIF-WF.Type: Information

###### ILAA-FBDI-GBDF-BBJJ_recommendederrorreaction: Recommended error reaction
System integrator to select an appropriate safe reaction in the SMU.
- ReqIF-WF.Type: Information

###### BBPA-FBDI-GBFC-EGCE: SM[SW]:SPU:SBST
The specification for SM[SW]:SPU:SBST can be found in Jama under Software Requirements (SWRQ) SBST SPU
- ReqIF-WF.Type: Heading

##### BAUA-FBEF-DIGB-AFDG: Alarms
SPU alarms
| Alarm name | Safety mechanism | Alarm flag to be cleared in |
| --- | --- | --- |
| SPU alarm | ACTYIVE_CONFIG_CHECK SEP_TRANSACTION_INTEGRITY DATA_PROTECTION TRIGGER_REDUNDANCY RIF_INTERFACE CONTROL_REDUNDANCY | SMU and SPU |
- IFX.Version: 1
- ReqIF-WF.Type: Information

##### YJGA-FAFF-IADC-IDCD: External safety mechanisms
- IFX.Version: 1
- ReqIF-WF.Type: Information

###### ONXA-FBDI-GBGC-HFEB: ESM[SW]:SPU:SBST
- IFX.Version: 1
- ReqIF-WF.Type: Heading

###### ONXA-FBDI-GBGC-HFEB_description: Description
SM[SW]:SPU:SBST provides the system with the capability to detect permanent faults in the SPU.
- ReqIF-WF.Type: Requirement

###### ONXA-FBDI-GBGC-HFEB_resetoperationalstate: Reset operational state
Not applicable.
- ReqIF-WF.Type: Information

###### ONXA-FBDI-GBGC-HFEB_configurationandactivation: Configuration and activation
The [Application SW] shall execute the SM[SW]:SPU:SBST every [DTI]. In case the test returns a "fail" result, the SPU engine shall be considered not reliable.
- ReqIF-WF.Type: Requirement

###### ONXA-FBDI-GBGC-HFEB_test: Test
Not applicable.
- ReqIF-WF.Type: Requirement

###### ONXA-FBDI-GBGC-HFEB_recommendederrorreaction: Recommended error reaction
System integrator to select appropriate safe reaction.
- ReqIF-WF.Type: Information

###### OJHA-FBDI-GBGG-DEAB: ESM[SW]:SPU:CONTROL_FLOW_SIGNATURE
- IFX.Version: 4
- ReqIF-WF.Type: Heading

###### OJHA-FBDI-GBGG-DEAB_description: Description
The system integrator shall configure SM[HW]:SPU:CONTROL_FLOW_SIGNATURE in a test environment by setting SM_CTRL.CCRCEN = 10b and initializing it by setting SM_USER.CINIT=10b. Please note that the CRC initialization value is kept until SM_USER.CINIT=01b is set. Also, the SM_CRCc_MASK registers may be used to mask out selected component CRCs from the control CRC calculation. After running a set of one or more static configurations in the SPU the data independent CRC shall be read from the CRC_CTRL_CRC register and recorded for later use in the real system.
During run-time on the real system, the application software shall activate SM[HW]:SPU:CONTROL_FLOW_SIGNATURE by setting SM_CTRL.CCRCEN = 10b. Each time, before running a configuration set, the application shall initialize the mechanism by setting SM_USER.CINIT=10b. Please note that the CRC initialization value is kept until SM_USER.CINIT=01b is set. The SM_CRCc_MASK registers shall be set to the same values as used in the test environment. The application software shall then read the computed CRC from the CRC_CTRL_CRC register after the SPU finishes processing the configuration set and compare it with its corresponding expected CRC. Upon detection of a mismatch, the application software shall trigger a safe reaction
- ReqIF-WF.Type: Requirement

###### CXQA-FBDI-GBHJ-DHGD: ESM[SW]:SPU:EXECUTION_TIME_CHECK
- IFX.Version: 4
- ReqIF-WF.Type: Heading

###### CXQA-FBDI-GBHJ-DHGD_description: Description
The time taken by the SPU to complete execution of a given configuration is predicable and repeatable except where the SPU is caused to stall by the trigger counter mechanism. A counter STATUS_EXTCNT is provided in the SPU to count clock cycles when the SPU is processing and this count is not affected by stalling. This counter is reset when the SPU is triggered and can be read when the SPU is idle. The value of this count after the execution of a given configuration can be compared to a value recorded from execution in a test environment. The application software can also detect SPU lock-up by setting a timeout, for example using the system timer (STM), to trigger if the SPU execution takes longer than the expected amount of time.
The system integrator shall configure the SPU in a test environment and run a set of one or more static configurations in the SPU. In the case there is more than one configuration these will take the form of a linked list, triggered once at the start, so that the count relates to the execution of the whole linked list. After the processing of the configurations by the SPU completes the value of the execution count shall be recorded to be used for comparison with the value of STATUS_EXTCNT read each time the SPU executes the same configuration set in the application. During run-time in the real system, the application software shall read STATUS_EXTCNT at the end of each execution of the configurations and compare it to the recorded value. If the values differ, then the application software shall trigger an appropriate safe reaction.
The number of SPU clock cycles taken to execute the configurations may be greater than the recorded value if the SPU is caused to stall by the trigger counter mechanism TRGCNT_ODM. When SPU is stalled it waits until the counter has been increment by, for example, the assertion of its ACK input. As this potential stalling is data-dependent, for example due to a high density of detected targets, any timeout should be set to take into account the worst case execution time for the configurations. The STATUS_EXTCNT value is not affected by this stalling behavior.
- ReqIF-WF.Type: Requirement

###### RIUA-FBDI-GBIA-HICB: ESM[SW]:SPU:ISR_MONITOR
- IFX.Version: 4
- ReqIF-WF.Type: Heading

###### RIUA-FBDI-GBIA-HICB_description: Description
This ESM shall detect missing or unintended interrupts originating from the SPU module. Usage of interrupts in this FB depends on the use cases and code implementation.
- Attention interrupts: When the SPU completes processing a configuration, linked list or programmed number of ramps it generates an interrupt to the interrupt router if configured to do so. The target interrupt service provider is either a processor capable of running software in an interrupt service routine or a peripheral such as the RDMA.
Where the target is a processor:
- Missing interrupts: If an interrupt generated by the SPU channel does not reach the intended target, the application software does not get notified of the completed operation. The application software shall detect such a missing interrupt by implementing a checking mechanism such as a timeout
- Unintended interrupts: If the SPU generates an unintended interrupt, the application software is notified too early or spuriously of an event in the SPU. The interrupt service routine implemented by the application software shall detect an unintended interrupt by reading the SPU STATUS_ATT0INT or STATUS_ATT1INT register, depending on the source of the interrupt and checking that the interrupt status is consistent with the masked interrupt sources and the MONITOR status register in the SPU
Where the target is not a processor the trigger counter, TRGCNT_ODM, shall be configured to count the interrupt events in the SPU and the number of acknowledgments from the target and for:
- Missing interrupts: The trigger counter will be decremented but not incremented as the target will not acknowledge the missing interrupt. In this case the counter will either reach zero or have a smaller than expected value at the end of execution of a configuration. Application software shall detect such a missing interrupt by checking the TRGCNT_ODM.CNT counter value after completion of execution of a configuration with the value configured by software before triggering the SPU
- Unintended interrupts: The trigger counter will be incremented but not decremented as the target will acknowledge the unintended interrupt. In this case the counter value will be greater than expected and this shall be checked as for missing interrupts
- Error interrupt: When the SPU encounters an error condition, the SPU generates an error interrupt to the interrupt router if configured to do so. The target interrupt service provider is usually a processor capable of running software in an interrupt service routine.
- Missing interrupts: If an error interrupt generated by the SPU does not reach the intended target, the application software does not get notified of the error condition. The application software shall detect such a missing interrupt by executing a periodic check of the SPU error status register STATUS_ERRINT for pending error conditions at least once within every fault-tolerant time interval
- Unintended interrupts: If the SPU generates an unintended error interrupt, the interrupt service routine implemented by the application software will not find any error flags set when it reads the SPU error status register STATUS_ERRINT. The application software shall trigger an appropriate reaction.
- ReqIF-WF.Type: Requirement

###### RVYA-FBDI-GBIF-JHHF: ESM[SW]:SPU:DATA_INTEGRITY
- IFX.Version: 5
- ReqIF-WF.Type: Heading

###### RVYA-FBDI-GBIF-JHHF_description: Description
Transient faults in the datapath or the control logic of the SPU will be cleared when the SPU is initialized for running the next configuration. Transient faults in the configuration will either be overwritten when a new configuration is loaded or detected by SM[HW]:SPU:ACTIVE_CFG_CHECK. Transient faults will therefore not be able to propagate across measurement cycles without detection. With respect to transient faults in the datapath or the control logic of the SPU occurring within a measurement cycle, these can be detected by performing feasibility checks on the results of the SPU processing using the inherent diversity.
The application software shall detect transient faults occurring within a measurement cycle by either comparing or integrating over results obtained from multiple antennae in an array or by comparing the results with those determined by predictive modeling from one acquisition to the next. Upon detection of an infeasible difference, an appropriate safe reaction shall be triggered.
- ReqIF-WF.Type: Requirement

#### GAAA-EDDG-BAJA-GAAH: Shared Resource Interconnect (SRI)
The Shared Resource Interconnect (SRI) is the connectivity fabric within AURIX™ devices for TriCore™ CPUs and high performance modules such as the DMA. A key component is the SRI crossbar, which connects all the agents in one SRI domain. The SRI crossbar carries the transactions between the SRI Masters and SRI Slaves of the same domain.
The SRI crossbar supports concurrent transactions between different SRI Master and SRI Slave agents. In addition it supports parallelism between each master and different slaves for read and write transactions as well as pipelining of all transactions between a master and slave.
The extends between multiple domains by the use of one or more bridges, and connects to other on-chip connectivity resources (FPI, LLI and AXI) through distinct bridges.
- IFX.Version: 1
- ReqIF-WF.Type: Information

##### OEAA-EGCJ-DJIA-CEAA: Internal safety mechanisms
- IFX.Version: 1
- ReqIF-WF.Type: Information

###### XEUA-EHCH-CGID-FJEI: SM[HW]:SRI:SRI_TRANSACTION_INTEGRITY
- IFX.Version: 20
- ReqIF-WF.Type: Heading

###### XEUA-EHCH-CGID-FJEI_description: Description
The SRI implements EDC encoders and decoders located in both SRI master and slave interfaces to detect errors occurring during an SRI transaction. Errors can be detected during the different phases of an SRI transaction, that is, the Address Phase, the Read Data phase and the Write Data phase.
Address phase errors:
The SRI master encodes the address and control signals with an EDC encoder during the address phase. The encoded signals are then checked at the target SRI slave.
Write Data phase errors:
During the write data phase, the SRI master encodes each beat of the write data along with its corresponding address with an EDC encoder. The encoded signals are then checked at the target SRI slave.
Read Data phase errors:
During the read data phase, the SRI slave encodes each beat of read data along with its corresponding address with an EDC encoder. The encoded signals are then checked at the target SRI master.
- ReqIF-WF.Type: Information

###### XEUA-EHCH-CGID-FJEI_resetoperationalstate: Reset operational state
The safety mechanisms are active directly after application reset.
- ReqIF-WF.Type: Information

###### XEUA-EHCH-CGID-FJEI_configurationandactivation: Configuration and activation
N.A.
- ReqIF-WF.Type: Requirement

###### XEUA-EHCH-CGID-FJEI_test: Test
These safety mechanisms can be tested for writes by using a Master Agent Function which supports error injection (for example, the CPU via the CPU_SEGEN register), and performing a write access which triggers the mechanism. They can be tested for reads by performing a read access to a Slave Agent Function which supports error injection.
- ReqIF-WF.Type: Requirement

###### XEUA-EHCH-CGID-FJEI_reporting: Reporting
EDC error reporting of SRI master and slave agents is explained in the user manual SRI chapter, subchapter “SRI EDC errors”. Please refer to the Alarms table at the end of this chapter for individual alarm names associated with this safety mechanism.
The SM maps to the following categories of alarms, linked to a specific transaction integrity check as detailed above. The number of alarms are implementation specific and are reported from the respective functional blocks with the following naming convention
- <FB_NAME> SRI Address Phase EDC Error
- <FB_NAME> SRI Write Data EDC Error
- <FB_NAME> SRI Read Data EDC Error
<FB_NAME> is a place holder for the name of the respective functional block.
- ReqIF-WF.Type: Information

###### XEUA-EHCH-CGID-FJEI_recommendederrorreaction: Recommended error reaction
System integrator to select appropriate safe reaction in SMU.
- ReqIF-WF.Type: Information

###### KEVA-EHCH-CHHF-BFHE: SM[HW]:SRI:SRI_ADDRESS_MAP_MONITORING
- IFX.Version: 1
- ReqIF-WF.Type: Heading

###### KEVA-EHCH-CHHF-BFHE_description: Description
Each SRI slave interface implements a mechanism to check that the address forwarded to it is within the expected range. If the address is not in the expected range, the slave interface responds with a bus error, which the default slave in the XBAR detects and raises an SRI XBAR Bus Error Event Alarm (or SRI XBAR SM Bus Error Event Alarm for special master accesses) for.
- ReqIF-WF.Type: Information

###### KEVA-EHCH-CHHF-BFHE_resetoperationalstate: Reset operational state
The safety mechanism is active directly after application reset.
- ReqIF-WF.Type: Information

###### KEVA-EHCH-CHHF-BFHE_configurationactivation: Configuration & activation
N.A.
- ReqIF-WF.Type: Requirement

###### KEVA-EHCH-CHHF-BFHE_test: Test
This safety mechanism cannot be directly tested by accesses through the interconnect.
- ReqIF-WF.Type: Requirement

###### KEVA-EHCH-CHHF-BFHE_reporting: Reporting
On detection of an address range violation the SMM signals Bus Error to the Interconnect which is detected by the XBAR that signals an Alarm_NCS or Alarm_CS alarm to SMU or SMUcs (depending if the cause of the error was security critical).
- ReqIF-WF.Type: Information

###### KEVA-EHCH-CHHF-BFHE_recommendederrorreaction: Recommended error reaction
System integrator to select appropriate safe reaction in SMU.
- ReqIF-WF.Type: Information

###### JZHA-EHCH-DCBE-EGHF: SM[HW]:SRI:SWAP_CONFIGURATION_PROTECTION
- IFX.Version: 1
- ReqIF-WF.Type: Heading

###### JZHA-EHCH-DCBE-EGHF_description: Description
The SRI XBAR implements a mechanism to ensure that SOTA enabling was setup as intended by monitoring inverted pairs of address values in the registers. If the address pairs are not complimentary, the SRI XBAR SOTA Swap Configuration Alarm is raised by the XBAR.
- ReqIF-WF.Type: Information

###### JZHA-EHCH-DCBE-EGHF_resetoperationalstate: Reset operational state
The safety mechanism is active directly after application reset.
- ReqIF-WF.Type: Information

###### JZHA-EHCH-DCBE-EGHF_configurationactivation: Configuration & activation
N.A.
- ReqIF-WF.Type: Requirement

###### JZHA-EHCH-DCBE-EGHF_test: Test
This safety mechanism can be tested by writing a pair of values into the registers which are not complimentary.
- ReqIF-WF.Type: Requirement

###### JZHA-EHCH-DCBE-EGHF_reporting: Reporting
On detection of a configuration violation the SMM signals an Alarm_NCS to SMU.
- ReqIF-WF.Type: Information

###### JZHA-EHCH-DCBE-EGHF_recommendederrorreaction: Recommended error reaction
System integrator to select appropriate safe reaction in SMU.
- ReqIF-WF.Type: Information

###### GGZA-EHCH-DCHJ-BGIH: SM[HW]:SRI:ERROR_HANDLING
- IFX.Version: 1
- ReqIF-WF.Type: Heading

###### GGZA-EHCH-DCHJ-BGIH_description: Description
If a bus error is detected by the SRI XBAR, the default slave captures the transaction and raises an SRI XBAR Bus Error Event Alarm (or SRI XBAR SM Bus Error Event Alarm for special master accesses) and an interrupt (or a special master interrupt for special master accesses).
If any SRI master or slave detects a transaction ID error, an error is signalled to the SRI XBAR, which then raises an SRI XBAR Bus Error Event Alarm (or SRI XBAR SM Bus Error Event Alarm for special master accesses) and an interrupt (or a special master interrupt for special master accesses).
- ReqIF-WF.Type: Information

###### GGZA-EHCH-DCHJ-BGIH_resetoperationalstate: Reset operational state
The safety mechanism is active directly after application reset.
- ReqIF-WF.Type: Information

###### GGZA-EHCH-DCHJ-BGIH_configurationactivation: Configuration & activation
N.A.
- ReqIF-WF.Type: Requirement

###### GGZA-EHCH-DCHJ-BGIH_test: Test
This safety mechanism can be tested by reading from a register location where no register is located within valid register space.
- ReqIF-WF.Type: Requirement

###### GGZA-EHCH-DCHJ-BGIH_reporting: Reporting
On detection of an error the SMM signals Bus Error to the Interconnect which is detected by the XBAR that signals an Alarm_NCS or Alarm_CS alarm to SMU or SMUcs (depending if the cause of the error was security critical).
- ReqIF-WF.Type: Information

###### GGZA-EHCH-DCHJ-BGIH_recommendederrorreaction: Recommended error reaction
System integrator to select appropriate safe reaction in SMU.
- ReqIF-WF.Type: Information

###### XVKA-EHCH-DCJA-EGIF: SM[HW]:SRI:SAFETY_ENDINIT
- IFX.Version: 1
- ReqIF-WF.Type: Heading

###### XVKA-EHCH-DCJA-EGIF_description: Description
The SRI provides a PROT mechanism (PROTSE) that protects the configuration of the master agent function identifier based access protection (ACCEN) to support freedom from interference of different SW tasks.
On a detected violation the access is blocked.
PROTSE: For the registers protected by PROTSE see tables Register Overview – Access Mode Glossary and Register Overview – SRI (ascending Offset Address) in User Manual.
- ReqIF-WF.Type: Information

###### XVKA-EHCH-DCJA-EGIF_resetoperationalstate: Reset operational state
The PROTSE mechanism is active after intentional configuration by application software.
- ReqIF-WF.Type: Information

###### XVKA-EHCH-DCJA-EGIF_configurationactivation: Configuration & activation
The PROTSE mechanism must be enabled and configured once via register PROTSE by application software. The alarm handling has to be configured in the SMU.
- ReqIF-WF.Type: Requirement

###### XVKA-EHCH-DCJA-EGIF_test: Test
This safety measure can be tested after the PROT owner has been configured:
Write access to a protected register by a master agent function that is not the PROT owner.
- ReqIF-WF.Type: Requirement

###### XVKA-EHCH-DCJA-EGIF_reporting: Reporting
On detection of an access protection violation the SRI will terminate the access with SRI error that is detected by the XBAR, see SM[HW]:SRI:ERROR_HANDLING.
- ReqIF-WF.Type: Information

###### XVKA-EHCH-DCJA-EGIF_recommendederrorreaction: Recommended error reaction
System integrator to select appropriate safe reaction in SMU.
- ReqIF-WF.Type: Information

###### PPCA-EHCH-CGGE-JIDJ: SM[HW]:SRI:SV_AP
- IFX.Version: 1
- ReqIF-WF.Type: Heading

###### PPCA-EHCH-CGGE-JIDJ_description: Description
Critical module registers are implemented with a write access restriction that restricts the write access to access with supervisor (SV) privilege.
On a detected violation the access is blocked.
For the registers protected by SV see tables Register Overview – Access Mode Glossary and Register Overview – SRI (ascending Offset Address) in User Manual.
- ReqIF-WF.Type: Information

###### PPCA-EHCH-CGGE-JIDJ_resetoperationalstate: Reset operational state
The safety mechanism is active after application reset.
- ReqIF-WF.Type: Information

###### PPCA-EHCH-CGGE-JIDJ_configurationactivation: Configuration & activation
The alarm handling has to be configured in the SMU.
- ReqIF-WF.Type: Requirement

###### PPCA-EHCH-CGGE-JIDJ_test: Test
This safety measure can be tested by an write access to a protected register by a master agent function without Supervisor (SV) access rights.
- ReqIF-WF.Type: Requirement

###### PPCA-EHCH-CGGE-JIDJ_reporting: Reporting
On detection of an access protection violation the SRI will terminate the access with SRI error that is detected by the XBAR, see SM[SRI]:FPI:ERROR_HANDLING.
- ReqIF-WF.Type: Information

###### PPCA-EHCH-CGGE-JIDJ_recommendederrorreaction: Recommended error reaction
System integrator to select appropriate safe reaction in SMU.
- ReqIF-WF.Type: Information

###### PKJA-EHCH-CGDJ-FFEB: SM[HW]:SRI:CFG_AS_AP
- IFX.Version: 10
- ReqIF-WF.Type: Heading

###### PKJA-EHCH-CGDJ-FFEB_description: Description
The SRI checks if the access master agent function identifier is enabled for the type of access (read access and write access, configured through the SRI ACCEN registers) to the selected register.
Unauthorized access attempts are blocked by this mechanism.
- ReqIF-WF.Type: Information

###### PKJA-EHCH-CGDJ-FFEB_resetoperationalstate: Reset operational state
An application reset will set the configuration of this safety mechanism back to its default value.
- ReqIF-WF.Type: Information

###### PKJA-EHCH-CGDJ-FFEB_configurationandactivation: Configuration and activation
This safety mechanism is active after intentional configuration by application software through the ACCENx registers.
- ReqIF-WF.Type: Requirement

###### PKJA-EHCH-CGDJ-FFEB_test: Test
This safety measure can be tested after the ACCENx has been configured:
Write access to a protected register by a master agent function that is not the ACCEN owner.
- ReqIF-WF.Type: Requirement

###### PKJA-EHCH-CGDJ-FFEB_reporting: Reporting
On detection of an access protection violation the SRI terminate the access with SRI error that is detected by the XBAR, see SM[HW]:SRI:ERROR_HANDLING.
- ReqIF-WF.Type: Information

###### PKJA-EHCH-CGDJ-FFEB_recommendederrorreaction: Recommended error reaction
System integrator to select an appropriate safe reaction in the SMU.
- ReqIF-WF.Type: Information

##### WXHA-EHBJ-CGAI-BIJE: Alarms
SRI alarms
| Alarm name | Safety mechanism | Alarm flag to be cleared in |
| --- | --- | --- |
| SRI XBAR SOTA Swap Configuration Alarm | SM[HW]:SRI:SWAP_CONFIGURATION_PROTECTION | SMU only |
| SRI XBAR Address Phase ECC Error Alarm | SM[HW]:SRI:SRI_TRANSACTION_INTEGRITY | SMU only |
| SRI XBAR Write Data ECC Error Alarm | SM[HW]:SRI:SRI_TRANSACTION_INTEGRITY | SMU only |
| SRI XBAR Bus Error Event Alarm | SM[HW]:SRI:SV_AP | SMU only |
| SRI XBAR Bus Error Event Alarm | SM[HW]:SCU:SAFETY_ENDINIT | SMU only |
| SRI XBAR Bus Error Event Alarm | SM[HW]:CFG_AS_AP | SMU only |
| SRI XBAR Bus Error Event Alarm | SM[HW]:SRI:SRI_ADDRESS_MAP_MONITORING | SMU only |
| SRI XBAR Bus Error Event Alarm | SM[HW]:SRI:ERROR_HANDLING | SMU only |
| SRI S2F Address Phase ECC Error Alarm | SM[HW]:SRI:SRI_TRANSACTION_INTEGRITY | SMU only |
| SRI S2F Write Data ECC Error Alarm | SM[HW]:SRI:SRI_TRANSACTION_INTEGRITY | SMU only |
| SRI F2S Read Data ECC Error Alarm | SM[HW]:SRI:SRI_TRANSACTION_INTEGRITY | SMU only |
| SRI S2A Address Phase ECC Error Alarm | SM[HW]:SRI:SRI_TRANSACTION_INTEGRITY | SMU only |
| SRI S2A Write Data ECC Error Alarm | SM[HW]:SRI:SRI_TRANSACTION_INTEGRITY | SMU only |
| SRI A2S Read Data ECC Error Alarm | SM[HW]:SRI:SRI_TRANSACTION_INTEGRITY | SMU only |
| SRI S2L Address Phase ECC Error Alarm | SM[HW]:SRI:SRI_TRANSACTION_INTEGRITY | SMU only |
| SRI S2L Write Data ECC Error Alarm | SM[HW]:SRI:SRI_TRANSACTION_INTEGRITY | SMU only |
| SRI G2S Read Data ECC Error Alarm | SM[HW]:SRI:SRI_TRANSACTION_INTEGRITY | SMU only |
| SRI XBAR Bus Error Event Alarm | SM[HW]:SRI:SV_AP SM[HW]:SRI:CFG_AS_AP SM[HW]:SRI:SAFETY_ENDINIT | SMU only |
- IFX.Version: 1
- ReqIF-WF.Type: Information

##### CGAA-FAED-GHDG-JFGG: External safety mechanisms
- IFX.Version: 1
- ReqIF-WF.Type: Information

###### RYYA-EHGD-GHIG-FIEJ: ESM[SW]:SRI:CONFIG_READBACK
- IFX.Version: 1
- ReqIF-WF.Type: Heading

###### RYYA-EHGD-GHIG-FIEJ_description: Description
The application software shall detect by reading back the values and comparing them to the expected configuration if the XBAR configuration registers are written incorrectly. Upon detection of a difference, an alarm shall be triggered.
- ReqIF-WF.Type: Requirement

###### RYYA-EHGD-GHIG-FIEJ_resetoperationalstate: Reset operational state
Application reset.
- ReqIF-WF.Type: Information

###### RYYA-EHGD-GHIG-FIEJ_configurationactivation: Configuration & activation
N.A.
- ReqIF-WF.Type: Requirement

###### RYYA-EHGD-GHIG-FIEJ_test: Test
N.A.
- ReqIF-WF.Type: Requirement

###### RYYA-EHGD-GHIG-FIEJ_reporting: Reporting
N.A.
- ReqIF-WF.Type: Information

###### RYYA-EHGD-GHIG-FIEJ_recommendederrorreaction: Recommended error reaction
N.A.
- ReqIF-WF.Type: Information

###### THUA-EHGD-GGHJ-JJJC: ESM[SW]:SRI:ERROR_HANDLING
- IFX.Version: 1
- ReqIF-WF.Type: Heading

###### THUA-EHGD-GGHJ-JJJC_description: Description
The application software shall evaluate for the SRI interrupts used by the application the stored diagnostic error information. The application software shall evaluate the type of SRI error by reading the PESTAT, ERRx and ERRADDRx registers and trigger the most appropriate reaction.
- ReqIF-WF.Type: Requirement

###### THUA-EHGD-GGHJ-JJJC_resetoperationalstate: Reset operational state
Application reset.
- ReqIF-WF.Type: Information

###### THUA-EHGD-GGHJ-JJJC_configurationactivation: Configuration & activation
N.A.
- ReqIF-WF.Type: Requirement

###### THUA-EHGD-GGHJ-JJJC_test: Test
N.A.
- ReqIF-WF.Type: Requirement

###### THUA-EHGD-GGHJ-JJJC_reporting: Reporting
N.A.
- ReqIF-WF.Type: Information

###### THUA-EHGD-GGHJ-JJJC_recommendederrorreaction: Recommended error reaction
N.A.
- ReqIF-WF.Type: Information

#### FQCA-EDEA-DBJA-FECB: Trace
Tracing is a non-intrusive observation that aids the debugging process, and supports profiling and trace based measurement applications.
The Trace functional block (TRACE) provides configuration, monitoring and event signaling functionality. It collects trace data and forwards it to a local storage called trace buffer from where it is sent out through one of the trace interfaces.
- IFX.Version: 1
- ReqIF-WF.Type: Information

##### RHEA-FAFF-ICGD-CACC: Internal safety mechanisms
This module cannot violate any safety goal. Therefore only the following safety mechanism is implemented.
- ReqIF-WF.Type: Information

###### QMMA-FBFF-IEJD-AAGH: SM[HW]:TRACE:CFG_AS_AP
- IFX.Version: 3
- ReqIF-WF.Type: Heading

###### QMMA-FBFF-IEJD-AAGH_description: Description
The MCDSxP and the TRIF check if the access master agent function identifier is enabled for the type of access (read access and write access, configured through the MCDSxP and TRIF ACCEN registers) to the selected register.
Unauthorized access attempts are blocked by this mechanism.
- ReqIF-WF.Type: Information

###### QMMA-FBFF-IEJD-AAGH_resetoperationalstate: Reset operational state
An application reset will set the configuration of this safety mechanism back to its default value.
- ReqIF-WF.Type: Information

###### QMMA-FBFF-IEJD-AAGH_configurationandactivation: Configuration and activation
This safety mechanism is active after intentional configuration by application software through the ACCENx registers.
- ReqIF-WF.Type: Requirement

###### QMMA-FBFF-IEJD-AAGH_test: Test
This safety measure can be tested after the ACCENx has been configured: Write access to a protected register by a master agent function that is not the ACCEN owner.
- ReqIF-WF.Type: Requirement

###### QMMA-FBFF-IEJD-AAGH_reporting: Reporting
On detection of an access protection violation the MCDSxP and the TRIF terminate the access with FPI error that is detected by the BCU, see SM[HW]:FPI:ERROR_HANDLING.
- ReqIF-WF.Type: Information

###### QMMA-FBFF-IEJD-AAGH_recommendederrorreaction: Recommended error reaction
The system integrator has to select an appropriate safe reaction in the SMU.
- ReqIF-WF.Type: Information

##### FPGA-EHBA-BGHC-JBGC: Alarms
The TRACE FB itself does not raise any safety alarms but the bus control unit does.
TRACE alarms
| Alarm name | Safety mechanism | Alarm flag to be cleared in |
| --- | --- | --- |
| FPI error alarm | SM[HW]:TRACE:CFG_AS_AP | SMU only |
- IFX.Version: 1
- ReqIF-WF.Type: Information

##### OEXA-FAFF-ICGD-FIFF: External safety mechanisms
This module cannot violate any safety goal. Therefore no external safety mechanism is required.
- ReqIF-WF.Type: Information

#### FAXA-EDCJ-DCIH-DHCA: Volatile Memory Test (VMT)
The Volatile Memory Test (VMT) controls and monitors the test, initialization and data integrity checking functions of the various internal memories in the device.
Each SRAM has digital logic surrounding it, known as SRAM Support Hardware (SSH). The SSH is a hardware block that controls the error detection and correction, Memory Built-In-Self-Test(MBIST) of internal memories. Each SSH block provides a unified interface for controlling its various functions. There are multiple such SSH instances, each of which controls one or more of the different internal memories. The VMT provides register interfaces to configure and control these various memory controllers.
- IFX.Version: 1
- ReqIF-WF.Type: Information

##### BKCA-FAFF-IDCI-EHHA: Internal safety mechanisms
- IFX.Version: 1
- ReqIF-WF.Type: Information

###### CYNA-EHED-IBEA-DIJF: SM[HW]:VMT:REG_MONITOR
- IFX.Version: 1
- ReqIF-WF.Type: Heading

###### CYNA-EHED-IBEA-DIJF_description: Description
The VMT implements safety flip-flops for detecting transient or permanent faults in the configuration registers and sequential logic. Safety flip-flops are special flip-flops that implement a hardware mechanism capable to detect bit flip within the flip-flops. The configuration and control registers which are designed with safety flip- flops are listed below:
MEMMAP/MEMMAPCS
RECCS/RECCSCS
RMEMCON/RMEMCONCS
MCi_RAMTEST/MCCSi_RAMTEST (protected bit-fields: all except SENSE)
MCi_ECCS/MCCSi_ECCS (protected bit-fields: MENE, ECCMAP, SFLE, BFLE)
MCi_ALMSRCS/MCCSi_ALMSRCS (protected bit-field: MISCE)
MCi_RCR/MCCSi_RCR (protected bit-field: VALID)
MCi_CONFIG2/MCCSi_CONFIG2 (protected bit-fields: BIWLSO, BIWLSE)
- ReqIF-WF.Type: Information

###### CYNA-EHED-IBEA-DIJF_resetoperationalstate: Reset operational state
This safety mechanism is reset according to the reset behavior of each of the registers above, as specified in the Register Overview - VMT table in the User Manual.
- ReqIF-WF.Type: Information

###### CYNA-EHED-IBEA-DIJF_configurationandactivation: Configuration and activation
N.A.
- ReqIF-WF.Type: Requirement

###### CYNA-EHED-IBEA-DIJF_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### CYNA-EHED-IBEA-DIJF_reporting: Reporting
After the monitor detects a fault, an alarm will be reported on the VMT UBS SFF Uncorrectable Error Alarm interface to SMU.
- ReqIF-WF.Type: Information

###### CYNA-EHED-IBEA-DIJF_recommendederrorreaction: Recommended error reaction
System integrator to select appropriate safe reaction in SMU.
- ReqIF-WF.Type: Information

###### ZDCA-EHED-IBGI-CIJD: SM[HW]:FB:CONTROL
- IFX.Version: 22
- ReqIF-WF.Type: Heading

###### ZDCA-EHED-IBGI-CIJD_description: Description
The VMT implements a detection of the following conditions of the surrounding logic of the SRAM:
- SSH test mode gets enabled by a fault (or by setting MEMTEST register) and thus the functional access of the SSH memories are not accessible (read or writable)
- SSH of security sensitive is enabled by a fault (or by setting MEMTEST register for security sensitive SSHs) and thus clearing/auto-initializing the memories is executed and they are not accessible
- Triggering of MBIST FSM, by a fault (or by setting MCONTROL.START)
- Triggering of Test features in the data path, leading to potential data corruption by a fault (or by activating LBIST)
- ReqIF-WF.Type: Information

###### ZDCA-EHED-IBGI-CIJD_resetoperationalstate: Reset operational state
An application reset will set the configuration of this safety mechanism back to its default value.
- ReqIF-WF.Type: Information

###### ZDCA-EHED-IBGI-CIJD_configurationandactivation: Configuration and activation
This mechanism is active after application reset.
- ReqIF-WF.Type: Requirement

###### ZDCA-EHED-IBGI-CIJD_test: Test
This mechanism can be tested through LBIST. Additionally UCE alarm needs to be generated by the application to test the alarm path. In order to trigger the UCE alarm, set the SSH into MBIST mode by setting the corresponding bit-field of register MEMTEST.
- ReqIF-WF.Type: Requirement

###### ZDCA-EHED-IBGI-CIJD_reporting: Reporting
After detection of any of these events, a VMT Uncorrectable error alarm will be reported to the SMU. In addition this is reflected as critical operational error in FAULTSTS.OPERR
- ReqIF-WF.Type: Information

###### ZDCA-EHED-IBGI-CIJD_recommendederrorreaction: Recommended error reaction
System integrator to select appropriate safe reaction in SMU.
- ReqIF-WF.Type: Information

###### GHOA-EHED-IBIG-BDJD: SM[HW]:FB:SM_CONTROL
- IFX.Version: 19
- ReqIF-WF.Type: Heading

###### GHOA-EHED-IBIG-BDJD_description: Description
The VMT implements the detection of the following events of the surrounding logic of the SRAM:
- Any of the alarm notifications of UCENE or CENE got disabled
- Any of the safety mechanisms got disabled (ECE, TRE, SBEm, DBE, ADDRE, OPENE)
- ReqIF-WF.Type: Information

###### GHOA-EHED-IBIG-BDJD_resetoperationalstate: Reset operational state
An application reset will set the configuration of this safety mechanism back to its default value.
- ReqIF-WF.Type: Information

###### GHOA-EHED-IBIG-BDJD_configurationandactivation: Configuration and activation
This mechanism is active after application reset.
- ReqIF-WF.Type: Requirement

###### GHOA-EHED-IBIG-BDJD_test: Test
This mechanism is tested through LBIST. Additionally ME alarm needs to be generated by application to test the alarm path. In order to trigger the ME alarm, reset any of the following bits: ECCS.ECE, ECCS.TRE, ECCS.UCENE, ECCS.ECENE, ALMSRCS.SBE, ALMSRCS.DBE, ALMSRCS.ADDRE, ALMSRCS.OVFE, ALMSRCS.OPENE.
- ReqIF-WF.Type: Requirement

###### GHOA-EHED-IBIG-BDJD_reporting: Reporting
After detection of any of these events, a VMT Miscellaneous Error alarm will be reported to the SMU. In addition this is reflected as error in FAULTSTS.MISCERR.
- ReqIF-WF.Type: Information

###### GHOA-EHED-IBIG-BDJD_recommendederrorreaction: Recommended error reaction
System integrator to select appropriate reaction in SMU.
- ReqIF-WF.Type: Information

###### AGMA-EHED-ICGH-EIGB: SM[HW]:FB:ADDRESS
- IFX.Version: 17
- ReqIF-WF.Type: Heading

###### AGMA-EHED-ICGH-EIGB_description: Description
The SRAM implements a mechanism to monitor the address generation logic. This mechanism detects failures due to wrong address generation or decoding during read and write operations.
This is achieved by providing each SRAM with a unique signature for each word, which is used to identify the word during read or write accesses. The signature is used to verify that an intended address is accessed during a read or write operation by calculating the expected signature and comparing against the stored signature.
- ReqIF-WF.Type: Information

###### AGMA-EHED-ICGH-EIGB_resetoperationalstate: Reset operational state
An application reset will set the configuration of this safety mechanism back to its default value.
- ReqIF-WF.Type: Information

###### AGMA-EHED-ICGH-EIGB_configurationandactivation: Configuration and activation
This mechanism is active after application reset.
- ReqIF-WF.Type: Requirement

###### AGMA-EHED-ICGH-EIGB_test: Test
This safety mechanism can be tested through simulating address faults in the address error detection by writing the ECCS.SFLE and checking the result in MCx_ECCD.UCERR.
- ReqIF-WF.Type: Requirement

###### AGMA-EHED-ICGH-EIGB_reporting: Reporting
Upon detection of a mismatch, a VMT Uncorrectable Error alarm will be reported to the SMU. In addition this is reflected in ECCD.UCERR.
In case of this alarm generation an entry into the ETRR register is made if ECCS.TRE is set.
- ReqIF-WF.Type: Information

###### AGMA-EHED-ICGH-EIGB_recommendederrorreaction: Recommended error reaction
System integrator to select appropriate safe reaction in SMU.
- ReqIF-WF.Type: Information

###### IDKA-EHED-ICDH-GJHA: SM[HW]:FB:ERROR_DETECTION
- IFX.Version: 1
- ReqIF-WF.Type: Heading

###### IDKA-EHED-ICDH-GJHA_description: Description
The SRAM implements a DED ECC logic. This mechanism detects SBE and DBE during read operations.
A fault in the data content stored in a SRAM can either be a single-bit error or double-bit error. An additional Signature Code is appended for the corresponding data content on every write access. During every read access, the Signature Codes are evaluated and in case of a mis-match, error in the data is detected.
Note: Some functional blocks implement for their local RAMs ERROR_DETECTION only while others implement both ERROR_DETECTION and ERROR_CORRECTION safety mechanisms. To find out which of these safety mechanisms are implemented in each FB RAM, please refer to the tables “SSH instances of VMTx” (x = VMT instance number) located in the device specific section of the VMT chapter in the user manual, subchapter “SSH Instances”. The column “ECC Type” shows SECDED for RAM memories implementing both safety mechanisms, DED for the ones implementing ERROR_DETECTION only and N/A for those without safety mechanisms.
- ReqIF-WF.Type: Information

###### IDKA-EHED-ICDH-GJHA_resetoperationalstate: Reset operational state
An application reset will set the configuration of this safety mechanism back to its default value.
- ReqIF-WF.Type: Information

###### IDKA-EHED-ICDH-GJHA_configurationandactivation: Configuration and activation
This mechanism is active after application reset.
- ReqIF-WF.Type: Requirement

###### IDKA-EHED-ICDH-GJHA_test: Test
This safety mechanism is tested by SM[HW]:FB:ECC_MONITOR during every data access to the RAM. If the system integrator wishes to test this safety mechanism before the start of the application, then the following procedure could be applied: write the data twice into the RAM, first with 'all-0' and then with 'all-1'. Read the data back after every write access. In case that a fault is detected, the SM[HW]:FB:ECC_MONITOR mechanism will generate an alarm.
- ReqIF-WF.Type: Requirement

###### IDKA-EHED-ICDH-GJHA_reporting: Reporting
Upon detection of an SBE or double-bit error , a VMT Uncorrectable Error alarm will be reported to the SMU
If this alarm is reported, an entry into the ETRR register is made if ECCS.TRE is set.
- ReqIF-WF.Type: Information

###### IDKA-EHED-ICDH-GJHA_recommendederrorreaction: Recommended error reaction
System integrator to select appropriate safe reaction in SMU.
- ReqIF-WF.Type: Information

###### CZZA-EHED-ICCA-AACI: SM[HW]:FB:ERROR_CORRECTION
- IFX.Version: 20
- ReqIF-WF.Type: Heading

###### CZZA-EHED-ICCA-AACI_description: Description
The SRAM implements a SEC-DED ECC logic. This mechanism detects SBE and DBE during read operations, SBE is also corrected if ECCS.ECE is set.
A fault in the data content stored in a SRAM can either be a single-bit error or double-bit error. An Error Correction Code is appended for the corresponding data content on every write access. During every read access, the Error Correction Codes are evaluated and in case of mis-match an error in the data is detected. In case of a single-bit error detection, it is possible to correct the error using the Error Correction Code.
Note: Some functional blocks implement for their local RAMs ERROR_DETECTION only while others implement both ERROR_DETECTION and ERROR_CORRECTION safety mechanisms. To find out which of these safety mechanisms are implemented in each FB RAM, please refer to the tables “SSH instances of VMTx” (x = VMT instance number) located in the device specific section of the VMT chapter in the user manual, subchapter “SSH Instances”. The column “ECC Type” shows SECDED for RAM memories implementing both safety mechanisms, DED for the ones implementing ERROR_DETECTION only and N/A for those without safety mechanisms.
- ReqIF-WF.Type: Information

###### CZZA-EHED-ICCA-AACI_resetoperationalstate: Reset operational state
An application reset will set the configuration of this safety mechanism back to its default value.
- ReqIF-WF.Type: Information

###### CZZA-EHED-ICCA-AACI_configurationandactivation: Configuration and activation
The correction of single bit errors is enabled by setting the ECCS.ECE bit.
- ReqIF-WF.Type: Requirement

###### CZZA-EHED-ICCA-AACI_test: Test
This safety mechanism is tested by SM[HW]:FB:ECC_MONITOR during every data access to the RAM. If the system integrator wishes to test this safety mechanism before the start of the application, then the following procedure could be applied: write the data twice into the RAM, first with 'all-0' and then with 'all-1'. Read the data back after every write access. In case that a fault is detected, the SM[HW]:FB:ECC_MONITOR mechanism will generate an alarm.
- ReqIF-WF.Type: Requirement

###### CZZA-EHED-ICCA-AACI_reporting: Reporting
Upon correction of an SBE a VMT Correctable Error alarm will be send to the SMU.
Upon detection of an DBE or ECE is disabled and SBE is detected a VMT Uncorrectable Error alarm will be send to the SMU.
If this alarm is reported, an accumulative entry into the ETRR register is made if ECCS.TRE is set.
- ReqIF-WF.Type: Information

###### CZZA-EHED-ICCA-AACI_recommendederrorreaction: Recommended error reaction
System integrator to select appropriate safe reaction in SMU.
- ReqIF-WF.Type: Information

###### ZQLA-EHED-ICFG-BHHF: SM[HW]:FB:ECC_MONITOR
- IFX.Version: 13
- ReqIF-WF.Type: Heading

###### ZQLA-EHED-ICFG-BHHF_description: Description
The SRAM implements a redundant hardware implementation of the ECC logic to detect faults in the Error Correction. This mechanism calculates the ECC codes in parallel and compares the results.
- ReqIF-WF.Type: Information

###### ZQLA-EHED-ICFG-BHHF_resetoperationalstate: Reset operational state
An application reset will set the configuration of this safety mechanism back to its default value.
- ReqIF-WF.Type: Information

###### ZQLA-EHED-ICFG-BHHF_configurationandactivation: Configuration and activation
This mechanism is active after application reset.
- ReqIF-WF.Type: Requirement

###### ZQLA-EHED-ICFG-BHHF_test: Test
N.A.
- ReqIF-WF.Type: Requirement

###### ZQLA-EHED-ICFG-BHHF_reporting: Reporting
Upon detection of a mismatch, a VMT Uncorrectable Error alarm will be send to the SMU.
- ReqIF-WF.Type: Information

###### ZQLA-EHED-ICFG-BHHF_recommendederrorreaction: Recommended error reaction
System integrator to select appropriate safe reaction in SMU.
- ReqIF-WF.Type: Information

###### GVJA-EHED-ICIG-FCCF: SM[HW]:FB:MBIST
- IFX.Version: 16
- ReqIF-WF.Type: Heading

###### GVJA-EHED-ICIG-FCCF_description: Description
The AURIX™ TC4xx implements a destructive MBIST algorithm that offers a higher permanent hardware random fault diagnostic coverage than the former non-destructive inversion test (NDIT). This provides the ability to detect structural problems of the SRAMs and to detect permanent random hardware faults in memory cells and memory controller.
- ReqIF-WF.Type: Information

###### GVJA-EHED-ICIG-FCCF_resetoperationalstate: Reset operational state
An application reset will set the configuration of this safety mechanism back to its default value.
- ReqIF-WF.Type: Information

###### GVJA-EHED-ICIG-FCCF_configurationandactivation: Configuration and activation
The application software shall execute the destructive MBIST test at least once per multi-point fault detection time interval (MPFDTI) on all SRAMs that are used by the application software. This includes both the key-on and the key-off test phases of the destructive MBIST algorithm. For a detailed description of the test procedure, please refer to the VMT chapter in the user manual, subchapter Destructive MBIST.
Note: During MBIST the SRAM under test can not be accessed. Therefore Application software shall prevent any attempt of R/W operations on the memory.
If MBIST is not performed, permanent random faults could remain latent in memory cells and memory controller.
- ReqIF-WF.Type: Requirement

###### GVJA-EHED-ICIG-FCCF_test: Test
N.A.
- ReqIF-WF.Type: Requirement

###### GVJA-EHED-ICIG-FCCF_reporting: Reporting
During
the key-on MBIST phase, critical errors are reported through the
ECCD register. Errors detected during
the key-off MBIST phase are reported by the MSTATUS and RDBFL register. For more details,
refer to the VMT chapter in the user manual, subchapter .
- ReqIF-WF.Type: Information

###### GVJA-EHED-ICIG-FCCF_recommendederrorreaction: Recommended error reaction
The
application software shall trigger an appropriate safe reaction if
an uncorrectable error is detected or if the number of accumulated
non-critical errors is greater than the allowed thresholds. These
are specified under the MSBE and MBLE
parameters in the device's datasheet.
- ReqIF-WF.Type: Information

###### PXAA-EHFA-GCCD-DICI: SM[HW]:FB:RAM_REG_MONITOR
- IFX.Version: 1
- ReqIF-WF.Type: Heading

###### PXAA-EHFA-GCCD-DICI_description: Description
The FB implements safety flip-flops for detecting transient or permanent faults in the configuration registers and sequential logic. Safety flip-flops are special flip-flops that implement a hardware mechanism capable to detect bit flip within the flip-flops. The configuration and control registers which are designed with safety flip- flops are listed below:
RCR.VALID
RAMTEST.R_ASTBL
RAMTEST.R_ASTWL
RAMTEST.R_PSTR
RAMTEST.PSTW
ALMSRCS.MISCE
ECCS.MENE
ECCS.ECCMAP
ECCS.SFLE
ECCS.BFLE
- ReqIF-WF.Type: Information

###### PXAA-EHFA-GCCD-DICI_resetoperationalstate: Reset operational state
This safety mechanism is reset according to the reset behavior of each of the registers above, as specified in the Register Overview -FB table in the User Manual.
- ReqIF-WF.Type: Information

###### PXAA-EHFA-GCCD-DICI_configurationandactivation: Configuration and activation
N.A.
- ReqIF-WF.Type: Requirement

###### PXAA-EHFA-GCCD-DICI_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### PXAA-EHFA-GCCD-DICI_reporting: Reporting
After the monitor detects a fault, an alarm is send from SSH to VMT which forwards it to the SMU as VMT Uncorrectable Error Alarm.
- ReqIF-WF.Type: Information

###### PXAA-EHFA-GCCD-DICI_recommendederrorreaction: Recommended error reaction
System integrator to select appropriate safe reaction in SMU.
- ReqIF-WF.Type: Information

###### SCXA-EHHJ-FAJC-FBDG: SM[HW]:VMT:ENDINIT
- IFX.Version: 1 1
- ReqIF-WF.Type: Heading

###### SCXA-EHHJ-FAJC-FBDG_description: Description
The VMT provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – VMT (ascending offset address) in the User Manual.
- ReqIF-WF.Type: Information

###### SCXA-EHHJ-FAJC-FBDG_resetoperationalstate: Reset operational state
An application reset will set the configuration of this safety mechanism back to its default value.
- ReqIF-WF.Type: Information

###### SCXA-EHHJ-FAJC-FBDG_configurationandactivation: Configuration and activation
This safety mechanism is active after intentional configuration by application software through the PROTE register.
- ReqIF-WF.Type: Requirement

###### SCXA-EHHJ-FAJC-FBDG_test: Test
This safety measure can be tested after the PROT owner has been configured:
Write access to a protected register by a master agent function that is not the PROT owner.
- ReqIF-WF.Type: Requirement

###### SCXA-EHHJ-FAJC-FBDG_reporting: Reporting
On detection of an access protection violation the VMT will terminate the access with FPI error that is detected by the BCU, see SM[HW]:FPI:ERROR_HANDLING.
- ReqIF-WF.Type: Information

###### SCXA-EHHJ-FAJC-FBDG_recommendederrorreaction: Recommended error reaction
System integrator to select an appropriate safe reaction in the SMU.
- ReqIF-WF.Type: Information

###### ESFA-EHHJ-FAJC-GDCJ: SM[HW]:VMT:SAFETY_ENDINIT
- IFX.Version: 10 10
- ReqIF-WF.Type: Heading

###### ESFA-EHHJ-FAJC-GDCJ_description: Description
The VMT provides PROT mechanisms (PROTSE, PROTCSE, PROTCSP) that protect the configuration of the access protection mechanism (ACCEN). The ACCEN mechanism is based on the master agent function identifier. This supports freedom from interference of different SW tasks.
Unauthorized access attempts are blocked by this mechanism.
For a list of the registers protected by PROTSE, PROTCSE and PROTCSP, see tables Register overview – access mode glossary and Register overview – VMT (ascending offset address) in the User Manual.
- ReqIF-WF.Type: Information

###### ESFA-EHHJ-FAJC-GDCJ_resetoperationalstate: Reset operational state
An application reset will set the configuration of this safety mechanism back to its default value.
- ReqIF-WF.Type: Information

###### ESFA-EHHJ-FAJC-GDCJ_configurationandactivation: Configuration and activation
This safety mechanism is active after intentional configuration by application software through the PROTSE, PROTCSE and PROTCSP registers.
- ReqIF-WF.Type: Requirement

###### ESFA-EHHJ-FAJC-GDCJ_test: Test
This safety measure can be tested after the PROT owner has been configured:
Write access to a protected register by a master agent function that is not the PROT owner.
- ReqIF-WF.Type: Requirement

###### ESFA-EHHJ-FAJC-GDCJ_reporting: Reporting
On detection of an access protection violation the VMT will terminate the access with FPI error that is detected by the BCU, see SM[HW]:FPI:ERROR_HANDLING.
- ReqIF-WF.Type: Information

###### ESFA-EHHJ-FAJC-GDCJ_recommendederrorreaction: Recommended error reaction
System integrator to select an appropriate safe reaction in the SMU.
- ReqIF-WF.Type: Information

###### AKYA-EHHJ-FAJC-FHBD: SM[HW]:VMT:CFG_AS_AP
- IFX.Version: 5 5
- ReqIF-WF.Type: Heading

###### AKYA-EHHJ-FAJC-FHBD_description: Description
The VMT checks if the access master agent function identifier is enabled for the type of access (read access and write access, configured through the VMT ACCEN registers) to the selected register.
Unauthorized access attempts are blocked by this mechanism.
- ReqIF-WF.Type: Information

###### AKYA-EHHJ-FAJC-FHBD_resetoperationalstate: Reset operational state
An application reset will set the configuration of this safety mechanism back to its default value.
- ReqIF-WF.Type: Information

###### AKYA-EHHJ-FAJC-FHBD_configurationandactivation: Configuration and activation
This safety mechanism is active after intentional configuration by application software through the ACCENx registers.
- ReqIF-WF.Type: Requirement

###### AKYA-EHHJ-FAJC-FHBD_test: Test
This safety measure can be tested after the ACCENx has been configured:
Write access to a protected register by a master agent function that is not the ACCEN owner.
- ReqIF-WF.Type: Requirement

###### AKYA-EHHJ-FAJC-FHBD_reporting: Reporting
On detection of an access protection violation the VMT terminate the access with FPI error that is detected by the BCU, see SM[HW]:FPI:ERROR_HANDLING.
- ReqIF-WF.Type: Information

###### AKYA-EHHJ-FAJC-FHBD_recommendederrorreaction: Recommended error reaction
System integrator to select an appropriate safe reaction in the SMU.
- ReqIF-WF.Type: Information

###### JCNA-EHHJ-FAJC-CDJD: SM[HW]:VMT:SV_AP
- IFX.Version: 1 1
- ReqIF-WF.Type: Heading

###### JCNA-EHHJ-FAJC-CDJD_description: Description
Critical module registers are implemented with a write access restriction that allows access only to masters with supervisor (SV) mode privilege.
Unauthorized access attempts are blocked by this mechanism.
For a list of the registers protected by SV, see tables Register overview – access mode glossary and Register overview – VMT (ascending offset address) in the User Manual.
- ReqIF-WF.Type: Information

###### JCNA-EHHJ-FAJC-CDJD_resetoperationalstate: Reset operational state
The safety mechanism is active after application reset.
- ReqIF-WF.Type: Information

###### JCNA-EHHJ-FAJC-CDJD_configurationandactivation: Configuration and activation
N.A.
- ReqIF-WF.Type: Requirement

###### JCNA-EHHJ-FAJC-CDJD_test: Test
This safety measure can be tested by an write access to a protected register by a master agent function without supervisor (SV) access rights.
- ReqIF-WF.Type: Requirement

###### JCNA-EHHJ-FAJC-CDJD_reporting: Reporting
On detection of an access protection violation the VMT will terminate the access with FPI error that is detected by the BCU, see SM[HW]:FPI:ERROR_HANDLING.
- ReqIF-WF.Type: Information

###### JCNA-EHHJ-FAJC-CDJD_recommendederrorreaction: Recommended error reaction
System integrator to select an appropriate safe reaction in the SMU.
- ReqIF-WF.Type: Information

##### WSAA-EHBJ-DHEG-DFAA: Alarms
VMT alarms
| Alarm name | Safety mechanism | Alarm flag to be cleared in |
| --- | --- | --- |
| VMT SFF Uncorrectable Error | SM[HW]:VMT:REG_MONITOR | SMU only |
| VMT Miscellaneous Error | SM[HW]:FB:SM_CONTROL | SMU only |
| VMT Correctable Error | SM[HW]:FB:ERROR_CORRECTION | SMU only |
| VMT Uncorrectable Error | SM[HW]:FB:CONTROL SM[HW]:FB:REG_MONITOR SM[HW]:FB:ERROR_CORRECTION SM[HW]:FB:ERROR_DETECTION SM[HW]:FB:ECC_MONITOR SM[HW]:FB:ADDRESS | SMU only |
| FPI error alarm | SM[HW]:VMT:SV_AP SM[HW]:VMT:CFG_AS_AP SM[HW]:VMT:ENDINIT SM[HW]:VMT:SAFETY_ENDINIT | SMU only |
- IFX.Version: 1
- ReqIF-WF.Type: Information

##### OBMA-FAFF-IDDJ-JBIJ: External safety mechanisms
- IFX.Version: 1
- ReqIF-WF.Type: Information

###### GYQA-EHHE-GBEJ-DJFA: ESM[SW]:VMT:ISR_MONITOR
- IFX.Version: 9
- ReqIF-WF.Type: Heading

###### GYQA-EHHE-GBEJ-DJFA_description: Description
Each VMT provides an interrupt request to the IR to notify the system of completion of all running tests (Memory Test Done Interrupt signal). Failure of notification signal is monitored by application software, which decides also the reaction.
To detect missing interrupts, the application software shall implement a timeout mechanism to establish whether the interrupt arrives inside the expected time window.
General MBIST sequence is shown below:
1. MBIST is started by application software (setting MCONTROL.START = 1) for respective SSHs to test
2. MEMDONE (respective bit) is set to 0 by HW
3. Application software sets MCONTROL.START = 0
4. HW sets MBISTDONE = 1 (as soon as test is finished and MCCONTROL.START = 0)
5. Interrupt is triggered by HW
A possible solution is to start a timeout after step 3. If interrupt is not set after the timeout has expired, the interrupt is missed.
Note: For interrupt timings, please refer to the IR chapter in the user manual, subchapter “Arbitration process”.
To detect unintended interrupts, the application software shall implement a state machine mechanism for functional monitoring. If the interrupt is received but current status is not compatible with the interrupt assertion, the interrupt is unintended. For example, Memory Test Done interrupt is supposed to be triggered only after intended MBIST activation.
- ReqIF-WF.Type: Requirement

###### GYQA-EHHE-GBEJ-DJFA_section2
- ReqIF-WF.Type: Information

###### GYQA-EHHE-GBEJ-DJFA_section3
- ReqIF-WF.Type: Information

#### DJIA-FDBJ-HGHH-FAFE: RAM safety mechanism instances
The following table shows the mapping between the safety mechanisms with a generic "SM[HW]:FB:xxx" designator located under Volatile Memory Test (VMT) and the ones that are actually implemented in this device. This ensures consistency with the safety mechanism names used in FMEDA.
Note: Even though these safety mechanisms are implemented in hardware, the AURIX™ TC4xx safety concept might not make use of them. This can be the case for example if there is another stronger safety mechanism covering faults originating from the RAM. Please refer to the integration requirements tables provided in the corresponding use cases under TLSR use cases to find out which safety mechanisms are needed.
Implemented SSH (VMT) safety
mechanisms per functional block
| Functional block name | Implemented SSH safety mechanisms | Comment |
| --- | --- | --- |
| ADC | SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR | ERROR_CORRECTION and ECC_MONITOR available only for CDSP Program RAM |
| CAN | SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR |  |
| CANXL | SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR |  |
| CPU | SM[HW]:FB:ERROR_DETECTION SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR | Error detection for PTAG only |
| CSRM | SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR | RAM corresponding to the PKC module |
| CSS | SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR |  |
| Debug and Trace | SM[HW]:FB:ADDRESS SM[HW]:FB:MBIST SM[HW]:FB:CONTROL SM[HW]:FB:SM_CONTROL SM[HW]:FB:RAM_REG_MONITOR | RAM corresponding to MCDS |
| DMA | SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR |  |
| HSPHY | SM[HW]:FB:ADDRESS SM[HW]:FB:MBIST SM[HW]:FB:CONTROL SM[HW]:FB:SM_CONTROL SM[HW]:FB:RAM_REG_MONITOR |  |
| LETH | SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR |  |
| NVMR | SM[HW]:FB:ERROR_CORRECTION SM[HW]:FB:ECC_MONITOR SM[HW]:FB:ADDRESS SM[HW]:FB:MBIST SM[HW]:FB:CONTROL SM[HW]:FB:SM_CONTROL SM[HW]:FB:RAM_REG_MONITOR | Check this entry with updated table |
| PPU | SM[HW]:FB:ADDRESS SM[HW]:FB:MBIST SM[HW]:FB:CONTROL SM[HW]:FB:SM_CONTROL SM[HW]:FB:RAM_REG_MONITOR |  |
| RDMA | SM[HW]:FB:ERROR_CORRECTION SM[HW]:FB:ECC_MONITOR SM[HW]:FB:ADDRESS SM[HW]:FB:MBIST SM[HW]:FB:CONTROL SM[HW]:FB:SM_CONTROL |  |
| SCR | SM[HW]:FB:ADDRESS SM[HW]:FB:MBIST SM[HW]:FB:CONTROL SM[HW]:FB:SM_CONTROL SM[HW]:FB:RAM_REG_MONITOR | - These safety mechanisms are implemented for the XRAM - ECC protection of XRAM is implemented in the SCR functional block, not in its SSH instance - Please refer to the user manual for more details about XRAM ECC |
| SPU | SM[HW]:FB:ERROR_CORRECTION SM[HW]:FB:ECC_MONITOR SM[HW]:FB:ADDRESS |  |
- IFX.Version: 4
- ReqIF-WF.Type: Information

#### QHVA-EDEA-DJBF-GIAA: Voltage and Temperature Monitors (VTMON)
The VTMON module interfaces to distributed temperature monitors at different locations across the microcontroller.
- IFX.Version: 1
- ReqIF-WF.Type: Information

##### ZEZA-FAFF-IDGB-HJBG: Internal safety mechanisms
- IFX.Version: 1
- ReqIF-WF.Type: Information

###### NPGA-EHEH-CEHB-DDBI: SM[HW]:VTMON:REG_MONITOR
- IFX.Version: 26
- ReqIF-WF.Type: Heading

###### NPGA-EHEH-CEHB-DDBI_description: Description
The VTMON implements safety flip-flops for detecting transient or permanent faults in the configuration registers and sequential logic. Safety flip-flops are special flip-flops that implement a hardware mechanism capable to detect bit flip within the flip-flops. The configuration and control registers which are designed with safety flip-flops are listed below:
DTSx_TRIM (x=0-4)
DTS_LIM1
DTSx_LIM1 (x=0-4)
DTS_LIM2
DTSx_LIM2 (x=0-4)
DTS_CON
DTSx_CON(x=0-4)
- ReqIF-WF.Type: Information

###### NPGA-EHEH-CEHB-DDBI_resetoperationalstate: Reset operational state
This safety mechanism is reset according to the reset behavior of each of the registers above, as specified in the tables Registers Overview - VTMON (ascending offset address) and Registers overview - PMS (ascending offset address) in the User Manual.
- ReqIF-WF.Type: Information

###### NPGA-EHEH-CEHB-DDBI_configurationandactivation: Configuration and activation
N.A.
- ReqIF-WF.Type: Requirement

###### NPGA-EHEH-CEHB-DDBI_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### NPGA-EHEH-CEHB-DDBI_reporting: Reporting
After the monitor detects a fault, an alarm will be reported on the VTMON SFF Uncorrectable Error alarm interface to SMU.
- ReqIF-WF.Type: Information

###### NPGA-EHEH-CEHB-DDBI_recommendederrorreaction: Recommended error reaction
System integrator to select appropriate safe reaction in SMU.
- ReqIF-WF.Type: Information

###### WADA-EHCH-DIAA-GFCI: SM[HW]:VTMON:TEMPERATURE_MONITOR
- IFX.Version: 1
- ReqIF-WF.Type: Heading

###### WADA-EHCH-DIAA-GFCI_description: Description
The digital temperature sensor monitors the junction temperature of the die with a resolution as specified in the datasheet. The inaccuracy of the DTS needs to be taken into account in form of substraction from the threshold to ensure no violation of the operating condition.
To prevent the DTS from common cause failure, the PMS and DTS instances are supplied from different power and reset domains.
- ReqIF-WF.Type: Information

###### WADA-EHCH-DIAA-GFCI_resetoperationalstate: Reset operational state
The PMS DTS instance is reset by LVD reset.
The VTMON DTS instances are reset by application reset.
- ReqIF-WF.Type: Information

###### WADA-EHCH-DIAA-GFCI_configurationandactivation: Configuration and activation
The threshold temperature is configured via bitfield DTSx_LIM1.UPPER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 in VTMON and DTS_LIM1.UPPER in PMS. The monitors can be enabled/disabled via bit DTSx_CON.EN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 in VTMON and DTS_CON.EN in PMS. The alarm generation is enabled/disabled via bit DTSx_CON.WRNEN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 in VTMON and DTS_CON_WREN in PMS.
Please refer to the User Manual for the default lower and upper warning thresholds of the DTS in VTMON and PMS. After application reset the VTMON instances of DTS are not enabled. The DTS in PMS is reset by LVD reset with the same reset limit values as the VTMON DTS instances and is also disabled after reset.
- ReqIF-WF.Type: Requirement

###### WADA-EHCH-DIAA-GFCI_test: Test
The description on how to test this safety mechanism can be found in the details of the following safety mechanism: ESM[SW]:VTMON:DTS_RESULT
- ReqIF-WF.Type: Requirement

###### WADA-EHCH-DIAA-GFCI_reporting: Reporting
The DTS status is updated regularly.
After the conversion time tM (as specified in datasheet) a fault would be reported on the monitoring alarm interface VTMON.DTSx over temperature alarm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 or PMS.DTS over temperature alarm to SMU.
- ReqIF-WF.Type: Information

###### WADA-EHCH-DIAA-GFCI_recommendederrorreaction: Recommended error reaction
System integrator to select appropriate safe reaction in SMU.
- ReqIF-WF.Type: Information

###### TGTA-EHHB-EJCF-JJAJ: SM[HW]:VTMON:ENDINIT
- IFX.Version: 1 1
- ReqIF-WF.Type: Heading

###### TGTA-EHHB-EJCF-JJAJ_description: Description
The VTMON provides a unique PROT mechanism (PROTE) that protects the configuration of the access protection mechanism (ACCEN). The ACCEN mechanism is based on the master agent function identifier. This supports freedom from interference of different SW tasks.
Unauthorized access attempts are blocked by this mechanism.
For a list of the registers protected by PROTE, see tables Register overview – access mode glossary and Register overview – VTMON (ascending offset address) in the User Manual.
- ReqIF-WF.Type: Information

###### TGTA-EHHB-EJCF-JJAJ_resetoperationalstate: Reset operational state
An application reset will set the configuration of this safety mechanism back to its default value.
- ReqIF-WF.Type: Information

###### TGTA-EHHB-EJCF-JJAJ_configurationandactivation: Configuration and activation
This safety mechanism is active after intentional configuration by application software through the PROTE register.
- ReqIF-WF.Type: Requirement

###### TGTA-EHHB-EJCF-JJAJ_test: Test
This safety measure can be tested after the PROT owner has been configured:
Write access to a protected register by a master agent function that is not the PROT owner.
- ReqIF-WF.Type: Requirement

###### TGTA-EHHB-EJCF-JJAJ_reporting: Reporting
On detection of an access protection violation the VTMON will terminate the access with FPI error that is detected by the BCU, see SM[HW]:FPI:ERROR_HANDLING.
- ReqIF-WF.Type: Information

###### TGTA-EHHB-EJCF-JJAJ_recommendederrorreaction: Recommended error reaction
System integrator to select an appropriate safe reaction in the SMU.
- ReqIF-WF.Type: Information

###### QBEA-EHHB-EJCE-GCDB: SM[HW]:VTMON:SAFETY_ENDINIT
- IFX.Version: 1 1
- ReqIF-WF.Type: Heading

###### QBEA-EHHB-EJCE-GCDB_description: Description
The VTMON provides a unique PROT mechanism (PROTSE) that protects the configuration of the access protection mechanism (ACCEN). The ACCEN mechanism is based on the master agent function identifier. This supports freedom from interference of different SW tasks.
Unauthorized access attempts are blocked by this mechanism.
For a list of the registers protected by PROTSE, see tables Register overview – access mode glossary and Register overview – VTMON (ascending offset address) in the User Manual.
- ReqIF-WF.Type: Information

###### QBEA-EHHB-EJCE-GCDB_resetoperationalstate: Reset operational state
An application reset will set the configuration of this safety mechanism back to its default value.
- ReqIF-WF.Type: Information

###### QBEA-EHHB-EJCE-GCDB_configurationandactivation: Configuration and activation
This safety mechanism is active after intentional configuration by application software through the PROTSE register.
- ReqIF-WF.Type: Requirement

###### QBEA-EHHB-EJCE-GCDB_test: Test
This safety measure can be tested after the PROT owner has been configured:
Write access to a protected register by a master agent function that is not the PROT owner.
- ReqIF-WF.Type: Requirement

###### QBEA-EHHB-EJCE-GCDB_reporting: Reporting
On detection of an access protection violation the VTMON will terminate the access with FPI error that is detected by the BCU, see SM[HW]:FPI:ERROR_HANDLING.
- ReqIF-WF.Type: Information

###### QBEA-EHHB-EJCE-GCDB_recommendederrorreaction: Recommended error reaction
System integrator to select an appropriate safe reaction in the SMU.
- ReqIF-WF.Type: Information

###### XVHA-EHHB-EJCE-IJBA: SM[HW]:VTMON:CFG_AS_AP
- IFX.Version: 5 5
- ReqIF-WF.Type: Heading

###### XVHA-EHHB-EJCE-IJBA_description: Description
The VTMON checks if the access master agent function identifier is enabled for the type of access (read access and write access, configured through the VTMON ACCEN registers) to the selected register.
Unauthorized access attempts are blocked by this mechanism.
- ReqIF-WF.Type: Information

###### XVHA-EHHB-EJCE-IJBA_resetoperationalstate: Reset operational state
An application reset will set the configuration of this safety mechanism back to its default value.
- ReqIF-WF.Type: Information

###### XVHA-EHHB-EJCE-IJBA_configurationandactivation: Configuration and activation
This safety mechanism is active after intentional configuration by application software through the ACCENx registers.
- ReqIF-WF.Type: Requirement

###### XVHA-EHHB-EJCE-IJBA_test: Test
This safety measure can be tested after the ACCENx has been configured:
Write access to a protected register by a master agent function that is not the ACCEN owner.
- ReqIF-WF.Type: Requirement

###### XVHA-EHHB-EJCE-IJBA_reporting: Reporting
On detection of an access protection violation the VTMON terminate the access with FPI error that is detected by the BCU, see SM[HW]:FPI:ERROR_HANDLING.
- ReqIF-WF.Type: Information

###### XVHA-EHHB-EJCE-IJBA_recommendederrorreaction: Recommended error reaction
System integrator to select an appropriate safe reaction in the SMU.
- ReqIF-WF.Type: Information

###### CWNA-EHHB-EJCE-IEBJ: SM[HW]:VTMON:SV_AP
- IFX.Version: 1 1
- ReqIF-WF.Type: Heading

###### CWNA-EHHB-EJCE-IEBJ_description: Description
Critical module registers are implemented with a write access restriction that allows access only to masters with supervisor (SV) mode privilege.
Unauthorized access attempts are blocked by this mechanism.
For a list of the registers protected by SV, see tables Register overview – access mode glossary and Register overview – VTMON (ascending offset address) in the User Manual.
- ReqIF-WF.Type: Information

###### CWNA-EHHB-EJCE-IEBJ_resetoperationalstate: Reset operational state
The safety mechanism is active after application reset.
- ReqIF-WF.Type: Information

###### CWNA-EHHB-EJCE-IEBJ_configurationandactivation: Configuration and activation
N.A.
- ReqIF-WF.Type: Requirement

###### CWNA-EHHB-EJCE-IEBJ_test: Test
This safety measure can be tested by an write access to a protected register by a master agent function without supervisor (SV) access rights.
- ReqIF-WF.Type: Requirement

###### CWNA-EHHB-EJCE-IEBJ_reporting: Reporting
On detection of an access protection violation the VTMON will terminate the access with FPI error that is detected by the BCU, see SM[HW]:FPI:ERROR_HANDLING.
- ReqIF-WF.Type: Information

###### CWNA-EHHB-EJCE-IEBJ_recommendederrorreaction: Recommended error reaction
System integrator to select an appropriate safe reaction in the SMU.
- ReqIF-WF.Type: Information

##### DNEA-EHBA-JAFH-JAFG: Alarms
VTMON alarms
| Alarm name | Safety mechanism | Alarm flag to be cleared in |
| --- | --- | --- |
| PMS.DTS over temperature alarm | SM[HW]:VTMON:TEMPERATURE:MONITOR | VTMON and SMU |
| VTMON.DTS00 over temperature alarm | SM[HW]:VTMON:TEMPERATURE:MONITOR | VTMON and SMU |
| VTMON.DTS1 over temperature alarm | SM[HW]:VTMON:TEMPERATURE:MONITOR | VTMON and SMU |
| VTMON.DTS2 over temperature alarm | SM[HW]:VTMON:TEMPERATURE:MONITOR | VTMON and SMU |
| VTMON.DTS3 over temperature alarm | SM[HW]:VTMON:TEMPERATURE:MONITOR | VTMON and SMU |
| VTMON.DTS4 over temperature alarm | SM[HW]:VTMON:TEMPERATURE:MONITOR | VTMON and SMU |
| VTMON SFF Uncorrectable Error alarm | SM[HW]:VTMON:REG_MONITOR | VTMON and SMU |
| FPI error alarm | SM[HW]:VTMON:SV_AP SM[HW]:VTMON:CFG_AS_AP SM[HW]:VTMON:ENDINIT SM[HW]:VTMON:SAFETY_ENDINIT | VTMON and SMU |
- IFX.Version: 1
- ReqIF-WF.Type: Information

##### DPWA-FAFF-IDGC-BDHD: External safety mechanisms
- IFX.Version: 1
- ReqIF-WF.Type: Information

###### SKVA-EHCH-EAFJ-EHEB: ESM[SW]:VTMON:DTS_RESULT
- IFX.Version: 1
- ReqIF-WF.Type: Heading

###### SKVA-EHCH-EAFJ-EHEB_description: Description
The application software shall read temperature measurement results of all VTMON DTS blocks and compare them to PMS DTS to detect latent faults.
Due to high probability of an unequal temperature distribution at different locations on the die and DTS inaccuracy, there will be a difference between two result values.
The central PMS DTS instance has to be compared to any of the VTMON DTS instances to cover the worst case temperature distribution.
The acceptable difference shall not exceed 6°C at every moment of time. Otherwise application software shall trigger a reaction.
- ReqIF-WF.Type: Requirement

###### SKVA-EHCH-EAFJ-EHEB_section2
The comparison is done by readout once per multi-point fault tolerant time interval of DTSx_STAT.RESULT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 and DTS_STAT.RESULT bits.
The comparison of DTSx_STAT.RESULT and DTS_STAT.RESULT can be also done on an alarm generation by application software. In case one of the DTS sensors triggers an over temperature alarm, the temperature results DTSx_STAT.RESULT and DTS_STAT.RESULT can be checked against each other for latent fault check.
- ReqIF-WF.Type: Information

#### QGCA-EDEA-DJFD-BJHB: Watchdog Timer Unit (WTU)
Watchdog timer unit (WTU) provides several independent watchdog timer (WDT) functions. The main system use of the WDT functions is program flow monitoring (PFM), tracking if the software is executing in the right order and is not stuck in a specific operation.
- IFX.Version: 1
- ReqIF-WF.Type: Information

##### SVQA-FAFF-IEBH-JIJJ: Internal safety mechanisms
- IFX.Version: 1
- ReqIF-WF.Type: Information

###### SDZA-EHFA-IBGJ-EJGE: SM[HW]:WTU:TEMPORAL_MONITORING
- IFX.Version: 11
- ReqIF-WF.Type: Heading

###### SDZA-EHFA-IBGJ-EJGE_description: Description
The WTU provides one dedicated watchdog timer (WDT) for each implemented CPU, for example CPU0 has WDTCPU0, CPU1 has WDTCPU1, etc, and one system WDT that is not assigned to a specific CPU and can be used by application software.
Each WDT contains a 16-bit up-counting timer with configurable base value. The timer operates on the fSPB clock domain with configurable division factor of 64, 256 or 16384.
For temporal program flow monitoring, the application software must refresh the timer before it runs into a timer overflow situation. In case of missing refresh the timer will overflow from 0xFFFF to 0x0000 and generates an alarm to the SMU. In case of emulated time-window mode, refresh value of 0x0000 has to be provided as an input to CTRLA.TCVI. Too early refresh results in an access error and an alarm is signaled to the SMU. A too late refresh results in timer overflow and an alarm is signaled to the SMU.
- ReqIF-WF.Type: Information

###### SDZA-EHFA-IBGJ-EJGE_resetoperationalstate: Reset operational state
This SM is reset by application reset.
- ReqIF-WF.Type: Information

###### SDZA-EHFA-IBGJ-EJGE_configurationandactivation: Configuration and activation
In order to use temporal monitoring functionality of a WDT the software shall configure the time deadline or time-window and enable the timer.
Changing configuration of the timer is done in three steps:
1. Unlock WDT by writing correct password and WDTx_CTRLA.LCK = '0'
2. Update shadow configuration by writing to WDTx_CTRLB register
3. Apply shadow configuration by writing WDTx_CTRLA.LCK = '1'
WDT is enabled by writing '0' to WDTx_CTRLB.DR bit-field. Timer base value is configured by writing to WDTx_CTRLB.TIMR bit-field, while frequency is selected by writing to WDTx_CTRLB.IFSR bit-field.
Once the basic configuration is set, refreshing the timer can be performed in two steps:
1. Unlock watchdog timer by writing correct password and LCK = '0' value into the WDTx_CTRLA register
2. Apply shadow configuration by writing LCK = '1' into the WDTx_CTRLA register
To use emulated time-window mode of a WDT, timer-check feature has to be enabled by writing '1' into WDTx_CTRLB.TCR. Setting the desired time-window size is done by writing to WDTx_CTRLB.TCTR bit-field.
- ReqIF-WF.Type: Requirement

###### SDZA-EHFA-IBGJ-EJGE_test: Test
During the normal operation, the software must service the watchdog timer before time deadline (overflow of the timer) or in given time-window to avoid the alarm to be generated. This safety mechanism can be tested by starting the timer and intentionally letting it overflow.
- ReqIF-WF.Type: Requirement

###### SDZA-EHFA-IBGJ-EJGE_reporting: Reporting
On detection of a WDT overflow or access error events an alarm is signaled to the SMU through the "WTU x WDT overflow or access error alarm" (x = CPU0-5,CPUcs,System).
- ReqIF-WF.Type: Information

###### SDZA-EHFA-IBGJ-EJGE_recommendederrorreaction: Recommended error reaction
System integrator to select appropriate safe reaction in SMU.
- ReqIF-WF.Type: Information

###### BYHA-EHEG-GEDE-CEEA: SM[HW]:WTU:REG_MONITOR
The WTU implements safety flip-flops for detecting transient or permanent faults in the configuration registers and sequential logic. The configuration and control registers, and bit-fields which are designed with safety flip-flops are:
- WDTCPUx_CTRLA.LCK (x = 0-5)
- WDTSYS_CTRLA.LCK
- WDTCPUx_CTRLB (x = 0-5)
- WDTSYS_CTRLB
- IFX.Version: 1
- ReqIF-WF.Type: Heading

###### BYHA-EHEG-GEDE-CEEA_description: Description
- ReqIF-WF.Type: Information

###### BYHA-EHEG-GEDE-CEEA_resetoperationalstate: Reset operational state
This safety mechanism is reset according to the reset behavior of each of the registers above, as specified in the Register Overview - WTU table in the User Manual.
- ReqIF-WF.Type: Information

###### BYHA-EHEG-GEDE-CEEA_configurationandactivation: Configuration and activation
N.A.
- ReqIF-WF.Type: Requirement

###### BYHA-EHEG-GEDE-CEEA_test: Test
The following software routine shall be used to run the self-test:
- GCC_RMi_CTL.TEz
- Setting GCC_RMi_CTL.TEz to 1 starts a self-test on the REG_MONITOR protected registers of a specified block instance i (refer to the register monitor mapping tables in device specific part of user manual)
- The application software has to set this bit back to 0 at the end of the self-test
- GCC_RMi_EF.EFz
- GCC_RMi_EF.EFz is set to 1 whenever a fault is detected in a REG_MONITOR protected register of a given specified block instance i, regardless of the state of the GCC_RMi_CTL.TEz
- The application software has to read this bit at the end of the self-test
- GCC_RMi_STS.STSz
- GCC_RMi_STS.STSz is set to 1 at the end of a REG_MONITOR self-test sequence
- The application software has to read this bit to check the final status of self-test
Moreover self-test routine for multiple functional blocks can be run in parallel by setting multiple bits in GCC_RMi_CTL register. Please refer to SMU chapter in user manual for more details on GCC_RMi_CTL, GCC_RMi_EF and GCC_RMi_STS registers.
- ReqIF-WF.Type: Requirement

###### BYHA-EHEG-GEDE-CEEA_reporting: Reporting
Upon detection of an error, an alarm will be reported to the SMU.
Alarms triggered by the SFFs activate the global "SFF_ALARM".
- ReqIF-WF.Type: Information

###### BYHA-EHEG-GEDE-CEEA_recommendederrorreaction: Recommended error reaction
System integrator to select the appropriate safe reaction in SMU.
- ReqIF-WF.Type: Information

###### OZBA-EHHJ-FAFF-FEHE: SM[HW]:WTU:SAFETY_ENDINIT
- IFX.Version: 1 1
- ReqIF-WF.Type: Heading

###### OZBA-EHHJ-FAFF-FEHE_description: Description
The WTU provides PROT mechanisms (WDTSEC_PROTCSE, WDTCPUy_PROTSE, WDTSYS_PROTSE) that protect the configuration of the access protection mechanism (ACCEN). The ACCEN mechanism is based on the master agent function identifier. This supports freedom from interference of different SW tasks.
Unauthorized access attempts are blocked by this mechanism.
For a list of the registers protected by WDTSEC_PROTCSE, WDTCPUy_PROTSE and WDTSYS_PROTSE, see tables Register overview – access mode glossary and Register overview – WTU (ascending offset address) in the User Manual.
- ReqIF-WF.Type: Information

###### OZBA-EHHJ-FAFF-FEHE_resetoperationalstate: Reset operational state
An application reset will set the configuration of this safety mechanism back to its default value.
- ReqIF-WF.Type: Information

###### OZBA-EHHJ-FAFF-FEHE_configurationandactivation: Configuration and activation
This safety mechanism is active after intentional configuration by application software through the WDTSEC_PROTCSE, WDTCPUy_PROTSE and WDTSYS_PROTSE and registers.
- ReqIF-WF.Type: Requirement

###### OZBA-EHHJ-FAFF-FEHE_test: Test
This safety measure can be tested after the PROT owner has been configured:
Write access to a protected register by a master agent function that is not the PROT owner.
- ReqIF-WF.Type: Requirement

###### OZBA-EHHJ-FAFF-FEHE_reporting: Reporting
On detection of an access protection violation the WTU will terminate the access with FPI error that is detected by the BCU, see SM[HW]:FPI:ERROR_HANDLING.
- ReqIF-WF.Type: Information

###### OZBA-EHHJ-FAFF-FEHE_recommendederrorreaction: Recommended error reaction
System integrator to select an appropriate safe reaction in the SMU.
- ReqIF-WF.Type: Information

###### GYAA-EHHJ-FAFF-EHFA: SM[HW]:WTU:CFG_AS_AP
- IFX.Version: 1 1
- ReqIF-WF.Type: Heading

###### GYAA-EHHJ-FAFF-EHFA_description: Description
The WTU checks if the access master agent function identifier is enabled for the type of access (read access and write access, configured through the WTU ACCEN registers) to the selected register.
Unauthorized access attempts are blocked by this mechanism.
- ReqIF-WF.Type: Information

###### GYAA-EHHJ-FAFF-EHFA_resetoperationalstate: Reset operational state
An application reset will set the configuration of this safety mechanism back to its default value.
- ReqIF-WF.Type: Information

###### GYAA-EHHJ-FAFF-EHFA_configurationandactivation: Configuration and activation
This safety mechanism is active after intentional configuration by application software through the ACCENx registers.
- ReqIF-WF.Type: Requirement

###### GYAA-EHHJ-FAFF-EHFA_test: Test
This safety measure can be tested after the ACCENx has been configured:
Write access to a protected register by a master agent function that is not the ACCEN owner.
- ReqIF-WF.Type: Requirement

###### GYAA-EHHJ-FAFF-EHFA_reporting: Reporting
On detection of an access protection violation the WTU terminate the access with FPI error that is detected by the BCU, see SM[HW]:FPI:ERROR_HANDLING.
- ReqIF-WF.Type: Information

###### GYAA-EHHJ-FAFF-EHFA_recommendederrorreaction: Recommended error reaction
System integrator to select an appropriate safe reaction in the SMU.
- ReqIF-WF.Type: Information

###### ZCQA-EHHJ-FAFF-CEFD: SM[HW]:WTU:SV_AP
- IFX.Version: 1 1
- ReqIF-WF.Type: Heading

###### ZCQA-EHHJ-FAFF-CEFD_description: Description
Critical module registers are implemented with a write access restriction that allows access only to masters with supervisor (SV) mode privilege.
Unauthorized access attempts are blocked by this mechanism.
For a list of the registers protected by SV, see tables Register overview – access mode glossary and Register overview – WTU (ascending offset address) in the User Manual.
- ReqIF-WF.Type: Information

###### ZCQA-EHHJ-FAFF-CEFD_resetoperationalstate: Reset operational state
The safety mechanism is active after application reset.
- ReqIF-WF.Type: Information

###### ZCQA-EHHJ-FAFF-CEFD_configurationandactivation: Configuration and activation
N.A.
- ReqIF-WF.Type: Requirement

###### ZCQA-EHHJ-FAFF-CEFD_test: Test
This safety measure can be tested by an write access to a protected register by a master agent function without supervisor (SV) access rights.
- ReqIF-WF.Type: Requirement

###### ZCQA-EHHJ-FAFF-CEFD_reporting: Reporting
On detection of an access protection violation the WTU will terminate the access with FPI error that is detected by the BCU, see SM[HW]:FPI:ERROR_HANDLING.
- ReqIF-WF.Type: Information

###### ZCQA-EHHJ-FAFF-CEFD_recommendederrorreaction: Recommended error reaction
System integrator to select an appropriate safe reaction in the SMU.
- ReqIF-WF.Type: Information

##### MAPA-EHBA-BDGH-FFIF: Alarms
WTU alarms
| Alarm name | Safety mechanism | Alarm flag to be cleared in |
| --- | --- | --- |
| WTU CPU0 WDT overflow or access error alarm | SM[HW]:WTU:TEMPORAL_MONITORING. | SMU only |
| WTU CPU1 WDT overflow or access error alarm | SM[HW]:WTU:TEMPORAL_MONITORING. | SMU only |
| WTU CPU2 WDT overflow or access error alarm | SM[HW]:WTU:TEMPORAL_MONITORING. | SMU only |
| WTU CPU3 WDT overflow or access error alarm | SM[HW]:WTU:TEMPORAL_MONITORING. | SMU only |
| WTU CPU4 WDT overflow or access error alarm | SM[HW]:WTU:TEMPORAL_MONITORING. | SMU only |
| WTU CPU5 WDT overflow or access error alarm | SM[HW]:WTU:TEMPORAL_MONITORING. | SMU only |
| WTU System WDT overflow or access error alarm | SM[HW]:WTU:TEMPORAL_MONITORING. | SMU only |
| WTU CPUcs WDT overflow or access error alarm | SM[HW]:WTU:TEMPORAL_MONITORING. | SMU only |
| WTU combined overflow or access error alarm | SM[HW]:WTU:TEMPORAL_MONITORING. | SMU only |
| WTU SFF uncorrectable error alarm | SM[HW]:WTU:REG_MONITOR. | SMU only |
| FPI error alarm | SM[HW]:WTU:SV_AP SM[HW]:WTU:CFG_AS_AP SM[HW]:WTU:SAFETY_ENDINIT | SMU only |
- IFX.Version: 1
- ReqIF-WF.Type: Information

##### EQEA-FAFF-IEBH-FJIJ: External safety mechanisms
- IFX.Version: 1
- ReqIF-WF.Type: Information

###### KUNA-EHEG-GEDB-FCCA: ESM[SW]:WTU:CONFIG_READBACK
The following registers of WTU have to be read back after write:
- WDTCPUy_CTRLA (y = 0-5)
- WDTCPUy_CTRLB (y = 0-5)
- WDTCPUy_SMUFSP (y = 0-5)
- WDTSYS_CTRLA
- WDTSYS_CTRLB
- WDTSYS_SMUFSP
The read-back values have to be compared with the expected values. In case of any difference the Application Software shall trigger a reaction.
Detailed explanation how watchdog timer operates can be found in WTU chapter WDT functionality.
- IFX.Version: 1
- ReqIF-WF.Type: Heading

###### KUNA-EHEG-GEDB-FCCA_description: Description
- ReqIF-WF.Type: Requirement

###### BKZA-EHEG-GEEJ-ACIB: ESM[SW]:WTU:TIMER_MONITOR
Application software shall use System Timer with the same clock configuration as WDT in order to check proper operation of a WDT. In that case errors in timer operation can be detected.
WDT will be configured according to the below given information:
- Unlock WDT by writing password and LCK = 0 to CTRLA register
- Write TIM R = 0000H, IFSR = 00H and DR = 0 into CTRLB register
- Write LCK = 1 to CTRLA register to apply configuration and start the WDT
STM timer should be started with matching timer increment frequency - select 16-bit out of 64-bit that will have same increment as WDT 16-bit timer.
Once WDT timer overflows to FFFFH, ignore the alarm and compare if the value of the selected 16-bit of the STM timer is also FFFFH or 0000H.
Upon detection of a mismatch between the two, a reaction shall be triggered via SW initiated alarm.
- IFX.Version: 1
- ReqIF-WF.Type: Heading

###### BKZA-EHEG-GEEJ-ACIB_description: Description
- ReqIF-WF.Type: Requirement

## ZDEA-EIAF-IEAI-GCGJ: TLSR use cases
| Disclamier for this Chapter |
| --- |
| This chapter is the result of a new approach followed by Infineon to provide a much improved guidance for system integrators. The contents of this chapter are still under development and in part incomplete. Please use this information as a reference only. |
This chapter describes the use cases and assumptions at system level that are relevant for the AURIX™ TC43x Microcontroller. It describes the general applications that the device is assumed to be used in. The safety assumptions which must be met and any recommended implementation measures are described.
The use cases are also called tlsr use case.The table below shows a summary of the tlsr use case s presented in this chapter.
The system integrator shall then select the tlsr use case s that are needed for the application. From this selection then the system integrator will be able to derive the safety mechanisms that shall be implemented: each tlsr use case shows, together with the assumptions of use s, and a list of the required safety mechanisms. The system integrator shall then implement the external safety mechanisms and activate/configure the safety mechanisms from this list.
Please note that some tlsr use case are always required in the context of a functional safe application (for example Power or Clock).
MCU Safety Related Functions
TUCs
| TLSR Name | TLSR Use Case (TUC) |
| --- | --- |
| Safe software execution platform [ASIL D] | Dedicated memory using system address map |
| Safe software execution platform [ASIL D] | Shared memory using hardware protection |
| Safe software execution platform [ASIL D] | Shared memory using software protection |
| Safe software execution platform [ASIL D] | Peripheral access |
| Safe software execution platform [ASIL D] | NVM access |
| Safe EEPROM access [ASIL B] | EEPROM access |
| Safe microcontroller unit infrastructure [ASIL D] | Interrupts |
| Safe microcontroller unit infrastructure [ASIL D] | DMA transaction |
| Safe microcontroller unit infrastructure [ASIL D] | Clock management |
| Safe microcontroller unit infrastructure [ASIL D] | Power management |
| Safe microcontroller unit infrastructure [ASIL D] | System mode management |
| Safe microcontroller unit infrastructure [ASIL D] | Volatile memory management |
| Safe co-processing [ASIL B] | Parallel processing for radar data |
| Safe MCU boot [ASIL D] | MCU boot |
| Safe digital acquisition [ASIL D] | Redundant GPI channels |
| Safe digital acquisition [ASIL D] | Redundant GPT12 channels |
| Safe analog acquisition [ASIL D] | Homogenous redundant ADC channels |
| Safe single input analog acquisition [ASIL B] | Single input redundant ADC channels |
| Safe digital actuation [ASIL D] | GPT12 output |
| Safe digital actuation [ASIL D] | GPO Output Read-Back |
| Safe MCU external communication [ASIL D] | Single communication channel |
| Safe MCU external communication [ASIL D] | Redundant communication channels |
| Safe MCU external communication [ASIL D] | External device configuration |
| Safe radar processing [ASIL B] | Radar input processing |
| Safe security management [ASIL D] | Cyber-security message authentication |
| Systematic fault avoidance of MCU [ASIL D] | Systematic fault avoidance |
Safe State Support TUCs
| TLSR Name | TLSR Use Case (TUC) |
| --- | --- |
| Internal failure reporting [ASIL D] | Internal failure reporting interface |
| External failure reporting [ASIL D] | External failure reporting interface |
| Alternate external failure reporting [ASIL D] | Alternate external failure reporting interface |
Dependent Failures TUCs
| TLSR Name | TLSR Use Case (TUC) |
| --- | --- |
| Avoidance or detection of common cause failure [ASIL D] | Common cause failure by power |
| Avoidance or detection of common cause failure [ASIL D] | Common cause failure by clock |
| Avoidance or detection of common cause failure [ASIL D] | Common cause failure by over-temperature |
| Avoidance or detection of common cause failure [ASIL D] | Common cause failure by system management |
| Avoidance or detection of common cause failure [ASIL D] | Common cause failure by Test and Debug functions |
| Avoidance or detection of common cause failure [ASIL D] | Common cause failure by common external resources |
| Coexistence of hardware elements [ASIL D] | Monitoring of slave access by unintended masters |
| Coexistence of software elements [ASIL D] | Monitoring of interference from software elements |
- IFX.Version: 16
- ReqIF-WF.Type: Information

### CSKA-EIAF-IECA-HGFE: Common for all use cases
- IFX.Version: 8
- ReqIF-WF.Type: Information

#### csk1591695318765-001
The system
integrator shall comply with the assumptions of
use and integration requirements specified for each use
case. The provided Automotive safety integrity
level of the safety requirements in Top Level Safety
Requirements are only valid when the
assumptions of
use and integration requirements are fulfilled.
- ReqIF-WF.Type: Requirement

#### csk1591695318765-002
The AURIX™
TC43x microcontroller is designed for several safety-related
applications as a safety element out of
context. This safety manual and the safety analysis
assume that the use of the device will conform to one or a combination of more
than one of these use cases.
- ReqIF-WF.Type: Requirement

#### RYOA-FJJA-GGDC-AAEB: Common assumptions of use
This section describes the safety assumptions in form of requirements for the application level integration of the device.
ASIL Level for External Safety Mechanisms
The safety mechanisms shown in this document were derived without performing Automotive safety integrity level decomposition. This means that all safety mechanisms inherit the Automotive safety integrity level level from the parent top level safety requirement.
For the system integrator this means that all the external safety mechanisms, either hardware or software, provided by him/her, shall be developed targeting the Automotive safety integrity level level of the parent top level safety requirement that the external safety mechanism is intended to cover.
Example: the ESM[SW]:CLOCK:CONFIG_READBACK shall be developed targeting ASIL D since its parent TLSR is Safe MCU Infrastructure [ASIL D].
| Type | Description | Comment |
| --- | --- | --- |
- IFX.Version: 9
- ReqIF-WF.Type: Information

##### ryo1600177431152-002
It is assumed that the system integrator implements the external safety mechanism specified in this document with the same ASIL level as the parent top level safety requirement that the external safety mechanism is targeting to fulfill.
System level assumptions of use
- ReqIF-WF.Type: Requirement

#### YLTA-EIAF-IEDH-HGBC: Application diagram
Please refer to the application diagram specific for each use case.
- IFX.Version: 5
- ReqIF-WF.Type: Information

#### JWJA-EIAF-IEEH-FFBE: Mission profile
Please refer to the FMEDA sheet and Safety analysis summary report (SASR) shown in the References chapter for detailed information about the operating conditions and mission profile.
- IFX.Version: 6
- ReqIF-WF.Type: Information

#### VRSA-EIAF-IEFH-FIBE: Product configuration
Please refer to the AURIX™ TC43x Datasheet for product specific configuration data and ratings.
- IFX.Version: 7
- ReqIF-WF.Type: Information

#### WFDA-FJJA-GGEB-FFFF: Internal and external safety mechanisms
This section lists the safety mechanisms that are always mandatory, regardless of the tlsr use case being used.
Currently, all required safety mechanisms are use-case specific.
- IFX.Version: 7
- ReqIF-WF.Type: Information

#### GEGA-EIAF-IEHA-JJDJ: Implementation hints
This section lists implementation hints that are always applicable, regardless of the tlsr use case being used.
Currently there are no general implementation hints to be mentioned here.
- IFX.Version: 8
- ReqIF-WF.Type: Information

### BPFA-FJEJ-HGDH-DECE: Dedicated memory using system address map
This tlsr use case is considering the scenario where a TriCore™ CPU with Lockstep (LS) monitoring enabled is accessing any of its dedicated memory resources using the System Address Map in linear mode.
These are:
- PSPR, DSPR and DLMU
- PCACHE and DCACHE
- Dedicated PFLASH or PRRAM bank(s)
Note: In the AURIX™ TC4xx Safety Concept it is considered that all safety relevant TriCore™ CPU operations are carried out by a TriCore™ CPU with LS monitoring enabled.
The safety measures derived from this TUC are shown under Internal and external safety mechanisms. These ensure the safety integrity of all the TriCore™ CPU operations in general and in particular the access to its dedicated memory resources. Some example operations are mentioned below.
The CPU can access its dedicated memory resources to execute code, to load or store variables and to load constants. In some cases, an instruction fetch request or data load or store request will be routed outside the CPU through the SRI bus and back into the CPU. A load request for a variable stored in PSPR would be an example for this.
Code can be fetched from the non-volatile memory (PFLASH or PRRAM) through the dedicated program flash interface (PFI) or from the local RAM. The CPU can execute the code by following the program flow as stored in the memory but also as a response to an NMI coming from the SCU or to an interrupt service request arriving from the interrupt router. Additionally, the CPU can send interrupt requests to the IR associated with events related to the system timer (STM) inside of it.
The selection of the address map mode is controlled by the SCU through the “SOTA control” interface. An error in SCU SOTA control logic can lead to wrong software execution. This applies even for devices that do not have SOTA support as the interface to SCU is implemented anyways.
- IFX.Version: 5
- ReqIF-WF.Type: Information

#### UAYA-FJEA-GJEA-EAFH: Specific assumptions of use
There are no specific assumptions of use for this use case.
- IFX.Version: 4
- ReqIF-WF.Type: Information

#### ANZA-FJEA-GJHD-AIAE: Application diagram
The application diagram below shows the functional blocks and interfaces involved in this tlsr use case. This TUC derives safety measures for those functional blocks and interfaces that are shown in colors. This TUC does not address the safety integrity of the functional blocks and interfaces shown in Black or Grey colors. In particular:
- The interrupt router is responsible for handling interrupt requests from the CPU and interrupt service requests going to the CPU. While safety integrity of the interrupt generation by the CPU and the interrupt servicing by the CPU is part of this TUC, the safety integrity of the interrupt handling done by the IR is addressed in the TUC Interrupts
- Safety integrity of the NMI execution is part of this TUC. The safety integrity of the NMI generation however is not, this is covered in the TUC Internal failure reporting interface
Application diagram for the TUC Dedicated memory using system address map
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- IFX.Version: 8
- ReqIF-WF.Type: Information

#### REBA-FJEA-GJIE-HCEC: Internal and external safety mechanisms
For this use case, the following internal safety mechanisms are considered to be configured, activated and used in addition to those stated in Internal and external safety mechanisms. All external safety mechanisms mentioned below shall be provided by the system integrator.
- IFX.Version: 16
- ReqIF-WF.Type: Information

##### REBA-FJEA-GJIE-HCEC-001
The system integrator shall ensure that the external safety mechanisms listed here are implemented and that the internal safety mechanisms listed here are configured and activated when using the TUC Dedicated memory using system address map:
ESM[SW]:MCU:LBIST
ESM[SW]:SMU:ALARM_SIGNAL_TEST
SM[HW]:CPU:CFI_LOCKSTEP
SM[HW]:CPU:CFI_LOCKSTEP_SCC
SM[HW]:CPU:CFI_PFRWB_ADDRESS_MONITOR
SM[HW]:CPU:CFI_WAIT_STATE_PROTECTION
SM[HW]:CPU:CODE_MPU
SM[HW]:CPU:DATA_MPU
SM[HW]:CPU:SWAP_MAP_SELECTION
SM[HW]:CPU:TRICORE_LOCKSTEP
SM[HW]:CPU:TRICORE_LOCKSTEP_SCC
SM[HW]:FB:ADDRESS
SM[HW]:FB:CONTROL
SM[HW]:FB:ERROR_CORRECTION
SM[HW]:FB:ECC_MONITOR
SM[HW]:FB:ERROR_DETECTION
SM[HW]:FB:MBIST
SM[HW]:FB:SM_CONTROL
SM[HW]:FPI:TRANSACTION_INTEGRITY
SM[HW]:MCU:LBIST
SM[HW]:MCU:LBIST_COMPLETE
SM[HW]:SCU:REG_MONITOR
SM[HW]:SMM:SAFE_FSM
SM[HW]:SRI:SRI_TRANSACTION_INTEGRITY
SM[HW]:WTU:TEMPORAL_MONITORING
- ReqIF-WF.Type: Requirement

##### REBA-FJEA-GJIE-HCEC-002
If the AURIX™ TC4xx MCU features the NVMR functional block, then the system integrator shall ensure that the external safety mechanisms listed here are implemented and that the internal safety mechanisms listed here are configured and activated when using the TUC Dedicated memory using system address map :
ESM[SW]:NVMR:CONFIG_READBACK
ESM[SW]:NVMR:PNVM_INTEGRITY_CHECK
ESM[SW]:NVMR:PNVM_UPDATE_CHECK
SM[HW]:NVMR:MISR
SM[HW]:NVMR:PNVM_ERROR_MANAGEMENT
SM[HW]:NVMR:PNVM_ECC_ONLINE_MONITOR
SM[HW]:NVMR:PNVM_WAIT_STATE_PROTECTION
SM[HW]:NVMR:REG_MONITOR
In addition to the safety mechanisms mentioned in the first row
- ReqIF-WF.Type: Requirement

##### REBA-FJEA-GJIE-HCEC-003
If the AURIX™ TC4xx MCU features the NVM functional block, then the system integrator shall ensure that the external safety mechanisms listed here are implemented and that the internal safety mechanisms listed here are configured and activated when using the TUC Dedicated memory using system address map :
ESM[SW]:NVM:CFG_READBACK
ESM[SW]:NVM:ISR_MONITOR
ESM[SW]:NVM:PFLASH_INTEGRITY_CHECK
ESM[SW]:NVM:PFLASH_WL_FAIL_DETECT
SM[HW]:NVM:BANK_MONITOR
SM[HW]:NVM:MISR
SM[HW]:NVM:PFLASH_ECC_ONLINE_CHECKER
SM[HW]:NVM:PFLASH_EDC_COMPARATOR
SM[HW]:NVM:PFLASH_ERROR_CORRECTION
SM[HW]:NVM:PFLASH_ERROR_MANAGEMENT
SM[HW]:NVM:PFLASH_WAIT_STATE_PROTECTION
SM[HW]:NVM:REG_MONITOR
In addition to the safety mechanisms mentioned in the first row
- ReqIF-WF.Type: Requirement

### SZBA-FJEJ-HGEH-JBFD: Shared memory using hardware protection
This tlsr use case is considering the scenario were a lockstep CPUx is accessing any of the dedicated memory resources of another CPUy using the system address map or sota address map A or B.
The memory resources are:
- program scratch pad ram, data scratch pad ram and distributed local memory unit
- 2 banks of non-volatile memory program flash
Note 1: In the AURIX™ TC43x Safety Concept, the lockstep-CPU is always considered as an actor of all safe software execution platform ASIL-D TUCs.
Note 2: In this TUC, CPUy is considered as a lockstep-CPU as well.
- IFX.Version: 4
- ReqIF-WF.Type: Information

#### FKRA-FJEB-GAGJ-JBBI: Specific assumptions of use
There are no specific assumptions of use for this use case.
- IFX.Version: 3
- ReqIF-WF.Type: Information

#### VHWA-FJEB-GAGA-AABD: Application diagram
The application diagram for this tlsr use case is shown below.
Application diagram for the tlsr use case Shared memory using hardware protection
APPLICATION DIAGRAM UNDER CONSTRUCTION
- IFX.Version: 6
- ReqIF-WF.Type: Information

#### JPRA-FJEB-GAGB-FGIB: Internal and external safety mechanisms
For this use case, the following Internal safety mechanisms are considered to be configured, activated and used in addition to those stated in Internal and external safety mechanisms. All external safety mechanisms mentioned below shall be provided by the system integrator.
- IFX.Version: 17
- ReqIF-WF.Type: Information

##### JPRA-FJEB-GAGB-FGIB-001
The system integrator shall ensure that the external safety mechanisms listed here are implemented and that the internal safety mechanisms listed here are configured and activated when using the TUC Shared memory using hardware protection:
ESM[SW]:MCU:LBIST
ESM[SW]:SMU:ALARM_SIGNAL_TEST
SM[HW]:CPU:CFI_LOCKSTEP
SM[HW]:CPU:CFI_LOCKSTEP_SCC
SM[HW]:CPU:CFI_PFRWB_ADDRESS_MONITOR
SM[HW]:CPU:CFI_WAIT_STATE_PROTECTION
SM[HW]:CPU:CODE_MPU
SM[HW]:CPU:DATA_MPU
SM[HW]:CPU:SWAP_MAP_SELECTION
SM[HW]:CPU:TRICORE_LOCKSTEP
SM[HW]:CPU:TRICORE_LOCKSTEP_SCC
SM[HW]:FB:ERROR_DETECTION
SM[HW]:FB:ERROR_CORRECTION
SM[HW]:FB:ECC_MONITOR
SM[HW]:FB:ADDRESS
SM[HW]:FB:MBIST
SM[HW]:FB:CONTROL
SM[HW]:FB:SM_CONTROL
SM[HW]:FPI:TRANSACTION_INTEGRITY
SM[HW]:MCU:LBIST
SM[HW]:MCU:LBIST_COMPLETE
SM[HW]:SCU:REG_MONITOR
SM[HW]:SMM:SAFE_FSM
SM[HW]:SRI:SRI_TRANSACTION_INTEGRITY
SM[HW]:WTU:TEMPORAL_MONITORING
- ReqIF-WF.Type: Requirement

##### JPRA-FJEB-GAGB-FGIB-002
The system integrator shall ensure that the external safety mechanisms listed here are implemented and that the internal safety mechanisms listed here are configured and activated IF the LMU is used in the context of the TUC Shared memory using hardware protection:
SM[HW]:FB:ERROR_CORRECTION
SM[HW]:FB:ADDRESS
SM[HW]:FB:MBIST
SM[HW]:FB:CONTROL
SM[HW]:FB:SM_CONTROL
SM[HW]:LMU:CONTROL_REDUNDANCY
SM[HW]:LMU:CONTROL_REDUNDANCY_SCC
SM[HW]:LMU:READ_WRITE_ECC
SM[HW]:LMU:TRANSACTION_INTEGRITY
In addition to the safety mechanisms mentioned in the first row
- ReqIF-WF.Type: Requirement

##### JPRA-FJEB-GAGB-FGIB-003
If the AURIX™ TC4xx MCU features the NVMR functional block, then the system integrator shall ensure that the external safety mechanisms listed here are implemented and that the internal safety mechanisms listed here are configured and activated when using the TUC Shared memory using hardware protection:
ESM[SW]:NVMR:CONFIG_READBACK
ESM[SW]:NVMR:PNVM_INTEGRITY_CHECK
ESM[SW]:NVMR:PNVM_UPDATE_CHECK
SM[HW]:NVMR:MISR
SM[HW]:NVMR:PNVM_ERROR_MANAGEMENT
SM[HW]:NVMR:PNVM_ECC_ONLINE_MONITOR
SM[HW]:NVMR:PNVM_WAIT_STATE_PROTECTION
SM[HW]:NVMR:REG_MONITOR
In addition to the safety mechanisms mentioned in the first row
- ReqIF-WF.Type: Requirement

##### JPRA-FJEB-GAGB-FGIB-004
If the AURIX™ TC4xx MCU features the NVM functional block, then the system integrator shall ensure that the external safety mechanisms listed here are implemented and that the internal safety mechanisms listed here are configured and activated when using the TUC Shared memory using hardware protection:
ESM[SW]:NVM:CFG_READBACK
ESM[SW]:NVM:ISR_MONITOR
ESM[SW]:NVM:PFLASH_INTEGRITY_CHECK
ESM[SW]:NVM:PFLASH_WL_FAIL_DETECT
SM[HW]:NVM:BANK_MONITOR
SM[HW]:NVM:MISR
SM[HW]:NVM:PFLASH_ECC_ONLINE_CHECKER
SM[HW]:NVM:PFLASH_EDC_COMPARATOR
SM[HW]:NVM:PFLASH_ERROR_CORRECTION
SM[HW]:NVM:PFLASH_ERROR_MANAGEMENT
SM[HW]:NVM:PFLASH_WAIT_STATE_PROTECTION
SM[HW]:NVM:REG_MONITOR
In addition to the safety mechanisms mentioned in the first row
- ReqIF-WF.Type: Requirement

### NLWA-FJEJ-HGFD-AJIH: Shared memory using software protection
This tlsr use case is considering the scenario were a lockstep CPUx is accessing a remote volatile memory without hardware protection using the system address map or sota address map A or B.
The memory resources are:
- Dedicated memory resources of a CPUy: program scratch pad ram, and distributed local memory unit
- Shared memory local memory unit
Note 1: In the AURIX™ TC43x Safety Concept, the LS-CPU is always considered as an actor of all safe software execution platform ASIL D TUCs.
Note 2: In this TUC, CPUy is considered as a CPU where the lockstep feature has been disabled (DLS-CPU).
- IFX.Version: 5
- ReqIF-WF.Type: Information

#### WGKA-FJEB-HAAA-IHBA: Specific assumptions of use
There are no specific assumptions of use for this use case.
- IFX.Version: 6
- ReqIF-WF.Type: Information

#### OUHA-FJEB-HAAC-JGHG: Application diagram
The application diagram for this tlsr use case is shown below.
Application diagram for the tlsr use case Shared memory using software protection
APPLICATION DIAGRAM UNDER CONSTRUCTION
- IFX.Version: 7
- ReqIF-WF.Type: Information

#### DGGA-FJEB-HAAD-EHCF: Internal and external safety mechanisms
For this use case, the following internal safety mechanisms are considered to be configured, activated and used in addition to those stated in Internal and external safety mechanisms. All external safety mechanisms mentioned below shall be provided by the system integrator.
- IFX.Version: 15
- ReqIF-WF.Type: Information

##### DGGA-FJEB-HAAD-EHCF-001
The system integrator shall implement the safety mechanisms listed here when using the TUC Shared memory using software protection:
ESM[SW]:CPU:DATA_INTEGRITY
ESM[SW]:MCU:LBIST
ESM[SW]:SMU:ALARM_SIGNAL_TEST
SM[HW]:CPU:DATA_MPU
SM[HW]:CPU:DLMU
SM[HW]:CPU:TRICORE_LOCKSTEP
SM[HW]:CPU:TRICORE_LOCKSTEP_SCC
SM[HW]:MCU:LBIST
SM[HW]:MCU:LBIST_COMPLETE
SM[HW]:SRI:SRI_TRANSACTION_INTEGRITY
SM[HW]:WTU:TEMPORAL_MONITORING
SM[HW]:CPU:DLMU can replace the ESM[SW]:CPU:DATA_INTEGRITY in case that the DLMU of the DLS CPU is used as a memory for safety-related data read and write.
- ReqIF-WF.Type: Requirement

##### DGGA-FJEB-HAAD-EHCF-003
The system integrator shall ensure that the external safety mechanisms listed here are implemented and that the internal safety mechanisms listed here are configured and activated IF the LMU is used in the context of the TUC Shared memory using software protection:
SM[HW]:LMU:CONTROL_REDUNDANCY
SM[HW]:LMU:CONTROL_REDUNDANCY_SCC
SM[HW]:LMU:READ_WRITE_ECC
SM[HW]:LMU:TRANSACTION_INTEGRITY
In addition to the safety mechanisms mentioned in the first row.
LMU is not available in all AURIX™ TC4xx devices.
- ReqIF-WF.Type: Requirement

### ZFFA-FJEJ-HGFB-JJBA: Peripheral access
A CPU may access a peripheral through the interconnect fabric while software element is running on the CPU.
Note on WTU in this TUC:
- The WTU provides the software execution platform with the ability to monitor the behavior of a CPU and the plausibility of a program sequence. Each CPU supports virtualization. If CPUx is configured to support virtualization, the hypervisor running on CPUx may control the associated CPU watchdog. A defective program sequence exists if the individual elements of a program are processed in the wrong sequence or period of time, or if the clock is faulty.
Note 1 - The system integrator may use the WTU as part of his/her safety mechanism. However, it is system integrator's responsibility to choose an appropriate program sequence monitoring method based on application use case.
Note 2 - In TC4xx Safety Concept, any fault of the WTU is classified as a dual point fault that contributes to the LFM only.
Note 3 - In the TC4xx Safety Concept, the LS-CPU is always considered as an actor of all Safe Software Execution Platform ASIL D TUCs.
In this TUC, the following tasks are analyzed:
1. Read data from peripheral
2. Write data to peripheral
- IFX.Version: 7
- ReqIF-WF.Type: Information

#### DDSA-FJEB-HJAD-FIFH: Specific assumptions of use
There are no specific assumptions of use for this use case.
- IFX.Version: 4
- ReqIF-WF.Type: Information

#### OLOA-FJEB-HJAF-JFBH: Application diagram
The application diagram for this tlsr use case is shown below.
Application diagram for the tlsr use case Peripheral access
APPLICATION DIAGRAM UNDER CONSTRUCTION
- IFX.Version: 5
- ReqIF-WF.Type: Information

#### ELJA-FJEB-HJAG-HBJJ: Internal and external safety mechanisms
For this use case, the following internal safety mechanisms are considered to be configured, activated and used in addition to those stated in Internal and external safety mechanisms. All external safety mechanisms mentioned below shall be provided by the system integrator.
- IFX.Version: 11
- ReqIF-WF.Type: Information

##### ELJA-FJEB-HJAG-HBJJ-001
The system integrator shall ensure that the external safety mechanisms listed here are implemented and that the internal safety mechanisms listed here are configured and activated when using the TUC Peripheral access:
ESM[SW]:MCU:LBIST
ESM[SW]:SMU:ALARM_SIGNAL_TEST
ESM[SW]:WTU:CONFIG_READBACK
ESM[SW]:WTU:TIMER_MONITOR
SM[HW]:CPU:DATA_MPU
SM[HW]:CPU:TRICORE_LOCKSTEP
SM[HW]:CPU:TRICORE_LOCKSTEP_SCC
SM[HW]:FPI:TRANSACTION_INTEGRITY
SM[HW]:MCU:LBIST
SM[HW]:MCU:LBIST_COMPLETE
SM[HW]:SRI:SRI_TRANSACTION_INTEGRITY
SM[HW]:WTU:REG_MONITOR
SM[HW]:WTU:TEMPORAL_MONITORING
- ReqIF-WF.Type: Requirement

### LHGA-FJEJ-HGFE-HAAC: NVM access
This TUC considers the safety integrity of the NVM PFLASH and EEPROM in terms of software execution platform. The EEPROM of the NVM are read through the SRI interconnect fabric. The application software may perform command sequences to update the EEPROM and PFLASH.
Note: Lockstep monitored CPU, the so called LS-CPU, is not motivated by the AURIX™ TC4xx Product Architecture. However, it is a well-trusted and state-of-the-art technology for safe processing unit in the market. Therefore, in the AURIX™ TC4xx Safety Concept, the LS-CPU is always an actor of all Safe Software Execution Platform ASIL D TUCs
In this TUC, the following operations are being considered:
1. Load data from EEPROM
2. Write operation on EEPROM or PFLASH
Note: The operations listed below are being covered by the TUC MCU boot:
1. Execute instruction from Boot ROM
2. Load data from configuration sector
3. Load data from user configuration block
- IFX.Version: 7
- ReqIF-WF.Type: Information

#### WTOA-FJEB-HBAF-JJED: Specific assumptions of use
Tere are no specific assumptions of use for this use case.
- IFX.Version: 3
- ReqIF-WF.Type: Information

#### LPXA-FJEB-HBAG-ABHI: Application Diagram
The application diagram for this tlsr use case is shown below.
Application diagram for the tlsr use case NVM access
APPLICATION DIAGRAM UNDER CONSTRUCTION
- IFX.Version: 5
- ReqIF-WF.Type: Information

#### WLQA-FJEB-HBAH-FJJI: Internal and external safety mechanisms
For this use case, the following Internal safety mechanisms are considered to be configured, activated and used in addition to those stated in Internal and external safety mechanisms. All external safety mechanisms mentioned below shall be provided by the system integrator.
- IFX.Version: 12
- ReqIF-WF.Type: Information

##### WLQA-FJEB-HBAH-FJJI-001
The system integrator shall ensure that the external safety mechanisms listed here are implemented and that the internal safety mechanisms listed here are configured and activated when using the TUC NVM access:
ESM[SW]:MCU:LBIST
ESM[SW]:SMU:ALARM_SIGNAL_TEST
SM[HW]:CPU:CFI_LOCKSTEP
SM[HW]:CPU:CFI_LOCKSTEP_SCC
SM[HW]:CPU:CFI_WAIT_STATE_PROTECTION
SM[HW]:CPU:DATA_MPU
SM[HW]:CPU:TRICORE_LOCKSTEP
SM[HW]:CPU:TRICORE_LOCKSTEP_SCC
SM[HW]:MCU:LBIST
SM[HW]:MCU:LBIST_COMPLETE
SM[HW]:SMM:SAFE_FSM
SM[HW]:SRI:SRI_TRANSACTION_INTEGRITY
SM[HW]:WTU:TEMPORAL_MONITORING
- ReqIF-WF.Type: Requirement

##### WLQA-FJEB-HBAH-FJJI-002
If the AURIX™ TC4xx MCU features the NVM functional block, then the system integrator shall ensure that the external safety mechanisms listed here are implemented and that the internal safety mechanisms listed here are configured and activated when using the TUC NVM access:
ESM[SW]:NVM:CFG_READBACK
ESM[SW]:NVM:EEPROM_DRIVER_D
ESM[SW]:NVM:ISR_MONITOR
ESM[SW]:NVM:PFLASH_INTEGRITY_CHECK
ESM[SW]:NVM:PFLASH_UPDATE_CHECK
ESM[SW]:NVM:PFLASH_WL_FAIL_DETECT
ESM[SW]:NVM:UCB_READBACK
SM[HW]:NVM:BANK_MONITOR
SM[HW]:NVM:MISR
SM[HW]:NVM:PFLASH_ECC_ONLINE_CHECKER
SM[HW]:NVM:PFLASH_EDC_COMPARATOR
SM[HW]:NVM:PFLASH_ERROR_CORRECTION
SM[HW]:NVM:PFLASH_ERROR_MANAGEMENT
SM[HW]:NVM:PFLASH_WAIT_STATE_PROTECTION
SM[HW]:NVM:REG_MONITOR
SM[HW]:FB:ADDRESS
SM[HW]:FB:CONTROL
SM[HW]:FB:ECC_MONITOR
SM[HW]:FB:ERROR_CORRECTION
SM[HW]:FB:MBIST
SM[HW]:FB:SM_CONTROL
In addition to the safety mechanisms mentioned in the first row.
- ReqIF-WF.Type: Requirement

##### WLQA-FJEB-HBAH-FJJI-003
If the AURIX™ TC4xx MCU features the NVMR functional block, then the system integrator shall ensure that the external safety mechanisms listed here are implemented and that the internal safety mechanisms listed here are configured and activated when using the TUC NVM access:
ESM[SW]:NVMR:CONFIG_READBACK
ESM[SW]:NVMR:EEPROM_DRIVER_D
ESM[SW]:NVMR:PNVM_INTEGRITY_CHECK
ESM[SW]:NVMR:PNVM_UPDATE_CHECK
ESM[SW]:NVMR:UCB_READBACK
SM[HW]:NVMR:MISR
SM[HW]:NVMR:PNVM_ERROR_MANAGEMENT
SM[HW]:NVMR:PNVM_ECC_ONLINE_MONITOR
SM[HW]:NVMR:PNVM_WAIT_STATE_PROTECTION
SM[HW]:NVMR:REG_MONITOR
In addition to the safety mechanisms mentioned in the first row.
- ReqIF-WF.Type: Requirement

### IMLA-FCCJ-GAGJ-FHBG: EEPROM access
This TUC covers the safety integrity of NVM EEPROM access in terms of storing and loading system integrator's safety-related data. The EEPROM of the NVM are read through the SRI interconnect fabric. The application software may perform command sequences to update the EEPROM.
In this TUC, the following operations are being considered:
1. Load data from EEPROM
2. Store data to EEPROM
Note: The operations listed below are being covered by the TUC MCU boot:
1. Execute instruction from Boot ROM
2. Load data from configuration sector
3. Load data from user configuration block
- IFX.Version: 2
- ReqIF-WF.Type: Information

#### NZIA-FDCA-ICGI-EEBD: Specific assumptions of use
There are no specific assumptions of use for this use case.
- IFX.Version: 2
- ReqIF-WF.Type: Information

#### SZXA-FDCB-JEEJ-GIII: Application diagram
The application diagram of this tlsr use case is shown below.
Application diagram for the tlsr use case EEPROM access
APPLICATION DIAGRAM UNDER CONSTRUCTION
- IFX.Version: 2
- ReqIF-WF.Type: Information

#### OWXA-FDCA-ACED-CBFE: Internal and external safety mechanisms
For this use case, the following internal safety mechanisms are considered to be configured, activated and used in addition to those stated in Internal and external safety mechanisms. All external safety mechanisms mentioned below shall be provided by the system integrator.
- IFX.Version: 6
- ReqIF-WF.Type: Information

##### OWXA-FDCA-ACED-CBFE-001
If the AURIX™ TC4xx MCU features the NVM functional block, then the system integrator shall ensure that the external safety mechanisms listed here are implemented and that the internal safety mechanisms listed here are configured and activated when using the TUC EEPROM access:
ESM[SW]:NVM:EEPROM_DRIVER_B
SM[HW]:NVM:REG_MONITOR
SM[HW]:SMM:SAFE_FSM
SM[HW]:SRI:SRI_TRANSACTION_INTEGRITY
- ReqIF-WF.Type: Requirement

##### OWXA-FDCA-ACED-CBFE-002
If the AURIX™ TC4xx MCU features the NVMR functional block, then the system integrator shall ensure that the external safety mechanisms listed here are implemented and that the internal safety mechanisms listed here are configured and activated when using the TUC EEPROM access:
ESM[SW]:NVMR:EEPROM_DRIVER_B
SM[HW]:NVMR:REG_MONITOR
SM[HW]:SMM:SAFE_FSM
SM[HW]:SRI:SRI_TRANSACTION_INTEGRITY
- ReqIF-WF.Type: Requirement

### IRQA-FJEJ-HGGA-BIII: Interrupts
The overarching principle of the interrupt system is that any interrupt service request may be serviced by any interrupt service provider.
The following functional blocks can be interrupt service providers:
- Central processing unit
- direct memory access
- generic timer module
- parallel processing unit
The following FB provides an arbitration function for multiple interrupt service requests:
- interrupt router
The signal flow through the interrupt system is composed of request, arbitration and service stages.
1. Request Stage
2. Arbitration Stage
3. Service Stage
- IFX.Version: 7
- ReqIF-WF.Type: Information

#### KWGA-FJEE-CBCB-CFCB: Specific assumptions of use
To make use of this tlsr use case, the system integrator shall ensure that the following assumptions of use are fulfilled:
- IFX.Version: 6
- ReqIF-WF.Type: Information

##### kwg1605532323632-001
In case the MCS inside GTM is used as an interrupt service provider, it is assumed that there are redundant interrupt request sources implemented by the system integrator that can be serviced by redundant MCS instances. For example, redundant ADC channels trigger the IR which in turn sends interrupt service requests to redundant MCS instances inside GTM.
Note: MCS instances from even GTM clusters shall be used redundantly with MCS instances from odd clusters.
Applicable only for AURIX™ TC4xx devices that feature the GTM module.
- ReqIF-WF.Type: Requirement

#### WLPA-FJEE-CBCC-DDJA: Application diagram
The application diagram for this tlsr use case is shown below.
Application diagram for the tlsr use case Interrupts
APPLICATION DIAGRAM UNDER CONSTRUCTION
- IFX.Version: 5
- ReqIF-WF.Type: Information

#### EIGA-FJEE-CBCE-FFAB: Internal and external safety mechanisms
For this use case, the following internal safety mechanisms are considered to be configured, activated and used in addition to those stated in Internal and external safety mechanisms. All external safety mechanisms mentioned below shall be provided by the system integrator.
- IFX.Version: 11
- ReqIF-WF.Type: Information

##### EIGA-FJEE-CBCE-FFAB-001
The system integrator shall ensure that the external safety mechanisms listed here are implemented and that the internal safety mechanisms listed here are configured and activated when using the TUC Interrupts:
ESM[SW]:IR:CONFIG_READBACK
ESM[SW]:IR:FFI_AVOIDANCE
ESM[SW]:MCU:LBIST
ESM[SW]:SMU:ALARM_SIGNAL_TEST
SM[HW]:FPI:TRANSACTION_INTEGRITY
SM[HW]:IR:ICU_MONITOR
SM[HW]:IR:LOCKSTEP
SM[HW]:IR:LOCKSTEP_SCC
SM[HW]:MCU:LBIST
SM[HW]:MCU:LBIST_COMPLETE
SM[HW]:WTU:TEMPORAL_MONITORING
- ReqIF-WF.Type: Requirement

##### EIGA-FJEE-CBCE-FFAB-002
If the GTM MCS is used to service interrupts, then the system integrator shall implement the following safety mechanism when using the TUC Interrupts:
ESM[SW]:GTM:INTERRUPT_REDUNDANCY
Not all AURIX™ TC4xx devices feature the GTM module
- ReqIF-WF.Type: Requirement

### NVOA-FJEJ-HGGB-EICF: DMA transaction
- The DMA moves data from a source module to a destination module without the intervention of a CPU.
- Any of the following functional block can be a DMA source or a DMA destination module. - lockstep-CPU's dedicated memories = DSPR, PSPR, DLMU, NVM PFLASH (local) - Safety related MCU memories = LMU, disabled LS-CPU's DLMU - Safety-related FB's memory, for example: = MCMCAN 'Data storage' = GTM monitoring registers (processing result register) = ADC monitoring registers (for example result register) = etc.
- Any of the following bus fabrics can be a data move path - SRI - FPI - LLI
- If the interconnect fabric transitions from one bus protocol to another bus protocol then an interconnect fabric bridge converts from one bus protocol to another bus protocol. The interconnect fabric bridge maintains the integrity of the payload. In this TUC, such bridges are described as followings. - S2F bridge: SRI to FPI bridge - S2L bridge: SRI to LLI bridge
- This TUC has the following sub use cases. 1) SUB1: DMA move data 2) SUB2: Pattern detection
- IFX.Version: 4
- ReqIF-WF.Type: Information

#### XEXA-FJEE-CCCA-FECG: Specific assumptions of use
There are no specific assumptions of use for this use case.
- IFX.Version: 3
- ReqIF-WF.Type: Information

#### IBDA-FJEE-CCCB-HCFD: Application diagram
The application diagram for this tlsr use case is shown below.
Application diagram for the tlsr use case DMA transaction
APPLICATION DIAGRAM UNDER CONSTRUCTION
- IFX.Version: 5
- ReqIF-WF.Type: Information

#### KAUA-FJEE-CCCC-IHEC: Internal and external safety mechanisms
For this use case, the following internal safety mechanisms are considered to be configured, activated and used in addition to those stated in Internal and external safety mechanisms. All external safety mechanisms mentioned below shall be provided by the system integrator.
- IFX.Version: 14
- ReqIF-WF.Type: Information

##### KAUA-FJEE-CCCC-IHEC-001
The system integrator shall ensure that the external safety mechanisms listed here are implemented and that the internal safety mechanisms listed here are configured and activated when using the TUC DMA transaction:
ESM[SW]:FPI:CONFIG_READBACK
ESM[SW]:MCU:LBIST
ESM[SW]:SMU:ALARM_SIGNAL_TEST
SM[HW]:DMA:LOCKSTEP
SM[HW]:DMA:LOCKSTEP_SCC
SM[HW]:FB:ERROR_CORRECTION
SM[HW]:FB:ECC_MONITOR
SM[HW]:FB:ADDRESS
SM[HW]:FB:MBIST
SM[HW]:FB:CONTROL
SM[HW]:FB:SM_CONTROL
SM[HW]:FPI:ERROR_HANDLING
SM[HW]:FPI:TRANSACTION_INTEGRITY
SM[HW]:LLI:ERROR_HANDLING
SM[HW]:LLI:TRANSACTION_INTEGRITY
SM[HW]:MCU:LBIST
SM[HW]:MCU:LBIST_COMPLETE
SM[HW]:SRI:ERROR_HANDLING
SM[HW]:SRI:SWAP_CONFIGURATION_PROTECTION
SM[HW]:SRI:SRI_TRANSACTION_INTEGRITY
SM[HW]:WTU:TEMPORAL_MONITORING
ESM[SW]:SRI:CONFIG_READBACK
- ReqIF-WF.Type: Requirement

### JPXA-FJEJ-HGGC-EIEF: Clock management
- External primary MCU clock source is an external clock(for example crystal or oscillator).
- The Clock Source function of the CLOCK generates the internal primary clock source by feeding back an amplified oscillation signal to the crystal through the TX path.
- The CLOCK uses the primary clock source for up-scaling, individual division and distribution of generated clocks for all MCU functions through the functional interface CLOCKS.
- Internal backup-clock is used for initialization and monitoring of system clock.
- IFX.Version: 4
- ReqIF-WF.Type: Information

#### QWMA-FJEE-CECD-FDCE: Specific assumptions of use
There are no specific assumptions of use for this use case.
- IFX.Version: 3
- ReqIF-WF.Type: Information

#### IAVA-FJEE-CECE-GIIJ: Application diagram
The application diagram for this tlsr use case is shown below.
Application diagram for the tlsr use case Clock management
APPLICATION DIAGRAM UNDER CONSTRUCTION
- IFX.Version: 5
- ReqIF-WF.Type: Information

#### WAUA-FJEE-CECG-JFII: Internal and external safety mechanisms
For this use case, the following internal safety mechanisms are considered to be configured, activated and used in addition to those stated in Internal and external safety mechanisms. All external safety mechanisms mentioned below shall be provided by the system integrator.
- IFX.Version: 10
- ReqIF-WF.Type: Information

##### WAUA-FJEE-CECG-JFII-001
The system integrator shall ensure that the external safety mechanisms listed here are implemented and that the internal safety mechanisms listed here are configured and activated when using the TUC Clock management:
ESM[SW]:CLOCK:CONFIG_READBACK
ESM[SW]:MCU:LBIST
ESM[SW]:SMU:ALARM_SIGNAL_TEST
ESM[HW]:SYS:WATCHDOG_FUNCTION
SM[HW]:CLOCK:ALIVE_MONITOR
SM[HW]:CLOCK:REG_MONITOR
SM[HW]:CLOCK:DIV_LCKSTP_MONITOR
SM[HW]:CLOCK:EVR_OSC_MONITOR
SM[HW]:CLOCK:PLL_LCKSTP_MONITOR
SM[HW]:CLOCK:PLL_LOL_MONITOR
SM[HW]:CLOCK:XTAL_OSC_MONITOR
SM[HW]:FPI:TRANSACTION_INTEGRITY
SM[HW]:MCU:LBIST
SM[HW]:MCU:LBIST_COMPLETE
- ReqIF-WF.Type: Requirement

### TPXA-FJEJ-HGGD-HAEF: Power management
The power management system (PMS) functional block provides the power infrastructure, generates supply voltages using internal voltage regulators, monitors supply voltages, facilitates power distribution. There are three main external supplies:
- Vddevrsb (5V or 3.3V, can be shorted with Vddext)
- Vddext (5V or 3.3V, mandatory)
- Vddextdc (3.3v or 5v or 6.5V, can be shorted with Vddext)
The selection which supplies are generated internally, is defined by dedicated package pins (HW configuration pins), the content of these pins is latched at startup.
This TUC addresses the safety integrity of the power supply system.
- IFX.Version: 5
- ReqIF-WF.Type: Information

#### AAYA-FJEE-CFBC-HCAF: Specific assumptions of use
To make use of this tlsr use case, the system integrator shall ensure that the following assumptions of use are fulfilled:
- IFX.Version: 5
- ReqIF-WF.Type: Information

##### aay1605536238316-001
It is assumed that the system integrator implements the external monitoring device which supervises the correct behavior of the power supply. In case it detects an over-voltage condition, the system shall disable the supply voltage to the microcontroller unit.
Rationale: a deviation above the specified maximum admitted voltage, can lead to permanent failures and physical damage to the device.
- ReqIF-WF.Type: Requirement

#### PNIA-FJEE-CFBD-FAFI: Application diagram
The application diagram for this tlsr use case is shown below.
Application diagram for the tlsr use case Power management
APPLICATION DIAGRAM UNDER CONSTRUCTION
- IFX.Version: 5
- ReqIF-WF.Type: Information

#### JAIA-FJEE-CFBF-JFCA: Internal and external safety mechanisms
For this use case, the following internal safety mechanisms are considered to be configured, activated and used in addition to those stated in Internal and external safety mechanisms. All external safety mechanisms mentioned below shall be provided by the system integrator.
- IFX.Version: 9
- ReqIF-WF.Type: Information

##### JAIA-FJEE-CFBF-JFCA-001
The system integrator shall implement the safety mechanisms listed here when using the TUC Power management:
ESM[HW]:SYS:WATCHDOG_FUNCTION
ESM[SW]:PMS:CONFIG_READBACK
SM[HW]:FPI:TRANSACTION_INTEGRITY
SM[HW]:PMS:REG_MONITOR
SM[HW]:PMS:SAFE_FSM
SM[HW]:PMS:SECONDARY_MONITOR
SM[HW]:PMS:STBY_CTRL
SM[HW]:PMS:VDDEVRSB_DET
- ReqIF-WF.Type: Requirement

### ZBGA-FJEJ-HGGE-HCEJ: System mode management
The system mode management coordinates the system mode transition between Reset, Stand-by, Run and Sleep. The functional blocks PMS, PORT, SMM, SMU and FW_RTC interact to realize the various system states by triggering and propagating the transition events.
- IFX.Version: 4
- ReqIF-WF.Type: Information

#### MIMA-FJEE-CFHC-JJHE: Specific assumptions of use
There are no specific assumptions of use for this use case.
- IFX.Version: 3
- ReqIF-WF.Type: Information

#### SFCA-FJEE-CFHD-DFJD: Application diagram
The application diagram for this tlsr use case is shown below.
Application diagram for the tlsr use case System mode management
APPLICATION DIAGRAM UNDER CONSTRUCTION
- IFX.Version: 5
- ReqIF-WF.Type: Information

#### EJDA-FJEE-CFHE-HGBE: Internal and external safety mechanisms
For this use case, the following internal safety mechanisms are considered to be configured, activated and used in addition to those stated in Internal and external safety mechanisms. All external safety mechanisms mentioned below shall be provided by the system integrator.
- IFX.Version: 10
- ReqIF-WF.Type: Information

##### EJDA-FJEE-CFHE-HGBE-001
The system integrator shall implement the safety mechanisms listed here when using the TUC System mode management:
ESM[SW]:SMU:ALARM_SIGNAL_TEST
ESM[HW]:SYS:WATCHDOG_FUNCTION
ESM[SW]:SMM:CONFIG_READBACK
SM[HW]:FPI:TRANSACTION_INTEGRITY
SM[HW]:PMS:SECONDARY_MONITOR
SM[HW]:SMM:REDUNDANT_CONTROL
SM[HW]:SMM:REG_MONITOR
SM[HW]:SMM:SAFE_FSM
SM[HW]:SMM:TIMEOUT_COUNTER
SM[HW]:SMU:ALIVE_MONITOR
SM[HW]:WTU:TEMPORAL_MONITORING
- ReqIF-WF.Type: Requirement

### CMRA-FJEJ-HGGG-JCCB: Volatile memory management
The MCU provides a testability for all volatile memories inside. There are 2 main purposes of volatile memory test.
- Each RAM is tested by a Memory Built In Self-Test (MBIST) function by MCU Firmware in order to check SRAM availability.
- Each RAM can be tested by system integrator's software to check if there is any permanent fault in the RAM that safety-related software accesses it.
- Each RAM has an ability to notify alarms by its own SSH (SRAM Support Hardware) and the VMT provides the CPU with the ability to access those SSH.
Note - The RAM test by MCU firmware is not considered in this TUC as the safety integrity of the firmware is part of MCU boot TUC.
- IFX.Version: 4
- ReqIF-WF.Type: Information

#### BANA-FJEE-CGDD-FECA: Specific assumptions of use
There are no specific assumptions of use for this use case.
- IFX.Version: 3
- ReqIF-WF.Type: Information

#### NLSA-FJEE-CGDF-JBHG: Application diagram
The application diagram for this tlsr use case is shown below.
Application diagram for the tlsr use case Volatile memory management
APPLICATION DIAGRAM UNDER CONSTRUCTION
- IFX.Version: 5
- ReqIF-WF.Type: Information

#### EAXA-FJEE-CGDF-IJBD: Internal and external safety mechanisms
For this use case, the following internal safety mechanisms are considered to be configured, activated and used in addition to those stated in Internal and external safety mechanisms. All external safety mechanisms mentioned below shall be provided by the system integrator.
- IFX.Version: 10
- ReqIF-WF.Type: Information

##### EAXA-FJEE-CGDF-IJBD-001
The system integrator shall ensure that the external safety mechanisms listed here are implemented and that the internal safety mechanisms listed here are configured and activated when using the TUC Volatile memory management:
ESM[SW]:MCU:LBIST
ESM[SW]:SMU:ALARM_SIGNAL_TEST
ESM[SW]:VMT:ISR_MONITOR
SM[HW]:FB:ADDRESS
SM[HW]:FB:CONTROL
SM[HW]:FB:ECC_MONITOR
SM[HW]:FB:ERROR_CORRECTION
SM[HW]:FB:ERROR_DETECTION
SM[HW]:FB:RAM_REG_MONITOR
SM[HW]:FB:SM_CONTROL
SM[HW]:FPI:TRANSACTION_INTEGRITY
SM[HW]:MCU:LBIST
SM[HW]:MCU:LBIST_COMPLETE
SM[HW]:VMT:REG_MONITOR
Please note that :FB: is a generic designator. Not all RAMs available in this product feature all these safety mechanisms. To find out which safety mechanisms are implemented in the RAM of a particular functional block, please refer to the chapter RAM safety mechanism instances
- ReqIF-WF.Type: Requirement

### HJSA-FEHG-DJEC-FIAA: Parallel processing for radar data
This tlsr use case is considering the scenario where the parallel processing unit is being used to process data originating from the radar interface (RIF). This can be applied for example when high performance post-processing of radar data is required without increasing the computational load of the TriCore™ CPU.
The data provided by the radar specific peripherals can either be moved directly to the PPU memory, for example with RDMA, or it can be loaded by the PPU from the microcontroller unit memory. Afterwards, the PPU stores the processed data to the MCU memory.
The PPU can perform the post-processing operations as a consequence of the program flow or based on interrupt requests forwarded by the interrupt router. After the post-processing task is finished, the PPU can signal this event through an interrupt request to the IR.
Common cause failure initiators
The potential Common Cause Failure initiators (CCFI) can affect both the mission and the monitoring logic simultaneously. Such a situation could lead to a violation of the safety goal. The table below shows the CCFI that are relevant for this TUC and the countermeasures that shall be applied to mitigate them:
| CCFI | Associated functional block | TUC addressing this CCFI |
| --- | --- | --- |
| Clock | CLOCK | Common cause failure by clock |
| Power | PMS | Common cause failure by power |
| Reset | SMM | Common cause failure by system management |
| product configuration | SCU | Common cause failure by system management |
| Logic test | TRI | Common cause failure by Test and Debug functions |
| Memory Test | VMT | Common cause failure by Test and Debug functions |
| Debug | Debug and trace | Common cause failure by Test and Debug functions |
- IFX.Version: 2
- ReqIF-WF.Type: Information

#### GGIA-FEHG-DJEF-HFFH: Specific assumptions of use
There are no specific assumptions of use for this use case.
- IFX.Version: 2
- ReqIF-WF.Type: Information

#### XVIA-FEHG-DJEG-IFDI: Application diagram
The application diagram below shows the functional blocks and interfaces involved in this tlsr use case. This TUC derives safety measures for those functional blocks and interfaces that are shown in colors. This TUC does not address the safety integrity of the functional blocks and interfaces shown in Black or Grey. In particular:
- The TriCore™ CPU plays a role in this TUC for example by writing the configuration registers of the PPU. However the safety integrity of these operations are addressed in the TUCs under the top level safety requirement "Safe software execution platform [ASIL D]"
- The NVMR can for example store the code that is executed for this application. The safety integrity of the NVMR is addressed in the TUC NVM access
- The functional blocks enclosed by the dashed box in the diagram below provide the safety relevant radar data that is then processed by the PPU. The safety integrity of the radar data is addressed in the TUC Radar input processing
- The interrupt router handles the interrupt requests from the PPU and interrupt service requests going to the PPU. The safety integrity of the interrupt handling is addressed in the TUC Interrupts
Application diagram for the TUC Paralell processing for radar data
- IFX.Version: 2
- ReqIF-WF.Type: Information

#### IJVA-FEHG-DJEI-GEDA: Internal and external safety mechanisms
For this use case, the following internal safety mechanisms are considered to be configured, activated and used in addition to those stated in Internal and external safety mechanisms. All external safety mechanisms mentioned below shall be provided by the system integrator.
- IFX.Version: 3
- ReqIF-WF.Type: Information

##### ijv1658740597541-001
The system integrator shall ensure that the external safety mechanisms listed here are implemented and that the internal safety mechanisms listed here are configured and activated when using the TUC Parallel processing for radar data:
ESM[SW]:PPU:CONFIG_READBACK
ESM[SW]:PPU:SHUTDOWN_REQUEST
ESM[SW]:PPU:STL
SM[HW]:IR:ICU_MONITOR
SM[HW]:LLI:TRANSACTION_INTEGRITY
SM[HW]:PPU:HW_REDUNDANCY
SM[HW]:PPU:DCACHE_ERROR_CORRECTION
SM[HW]:PPU:ICACHE_ERROR_CORRECTION
SM[HW]:PPU:CSM_ERROR_CORRECTION
SM[HW]:PPU:VDSP_ERROR_CORRECTION
SM[HW]:PPU:DUAL_RAIL_SIGNALS
SM[HW]:PPU:TSC_COMPARATOR
SM[HW]:PPU:REG_MONITOR
SM[HW]:PPU:REGISTER_EDC
SM[HW]:PPU:REGISTER_PARITY
SM[HW]:PPU:SHUTDOWN_FSM
SM[HW]:PPU:WATCHDOG_TIMER
SM[HW]:SRI:SRI_TRANSACTION_INTEGRITY
- ReqIF-WF.Type: Requirement

### HCKA-FJEJ-HGHB-IEBJ: MCU boot
This TUC considers the scenario where the system firmware (SYS_FW) is being executed. The SYS_FW is executed in the several operating modes of the MCU. However only the two shown below are considered as safety-related operating modes:
1) MCU start-up
2) MCU shutdown
Note: There are 3 more operating modes of the MCU where the SYS_FW is executed which however are not considered ad safety-related operating modes:
1) MCU standby mode
2) MCU production test mode
3) Debugging mode
- IFX.Version: 5
- ReqIF-WF.Type: Information

#### NITA-FJEE-CHFA-EFGG: Specific assumptions of use
To make use of this tlsr use case, the system integrator shall ensure that the following assumptions of use are fulfilled:
- IFX.Version: 5
- ReqIF-WF.Type: Information

##### nit1605538615677-002
It is assumed that the system is in a safe state while the MCU boot sequence is carried out.
- ReqIF-WF.Type: Requirement

##### nit1605538615677-003
It is assumed that, during the MCU boot sequence, the system integrator monitors the transition time to the fault free state from the start-up of the MCU boot sequence based on the tWCST parameter specified in the device's datasheet. If the MCU boot sequence execution time exceeds the specified time, the system stays in the safe state.
- ReqIF-WF.Type: Requirement

#### WVWA-FJEE-DBJH-FCHE: Application diagram
The application diagram for this tlsr use case is shown below.
Application diagram for the tlsr use case MCU boot
- IFX.Version: 3
- ReqIF-WF.Type: Information

#### RDVA-FJEE-DBCH-HDEE: Internal and external safety mechanisms
For this use case, the following Internal safety mechanisms are considered to be configured, activated and used in addition to those stated in Internal and external safety mechanisms. All external safety mechanisms mentioned below shall be provided by the system integrator.
- IFX.Version: 11
- ReqIF-WF.Type: Information

##### RDVA-FJEE-DBCH-HDEE-001
The system integrator shall ensure that the external safety mechanisms listed here are implemented and that the internal safety mechanisms listed here are configured and activated when using the TUC MCU boot:
SM[HW]:CPU:CFI_LOCKSTEP
SM[HW]:CPU:CFI_LOCKSTEP_SCC
SM[HW]:CPU:CFI_PFRWB_ADDRESS_MONITOR
SM[HW]:CPU:CFI_WAIT_STATE_PROTECTION
SM[HW]:SMM:SAFE_FSM
SM[HW]:SRI:SRI_TRANSACTION_INTEGRITY
SM[HW]:WTU:TEMPORAL_MONITORING
- ReqIF-WF.Type: Requirement

##### RDVA-FJEE-DBCH-HDEE-002
If the AURIX™ TC4xx MCU features the NVM functional block, then the system integrator shall ensure that the external safety mechanisms listed here are implemented and that the internal safety mechanisms listed here are configured and activated when using the TUC MCU boot:
SM[HW]:NVM:MISR
SM[HW]:NVM:BOOTROM_ADDR_PROTECTION
SM[HW]:NVM:BOOTROM_ERROR_CORRECTION
SM[HW]:NVM:PFLASH_ECC_ONLINE_CHECKER
SM[HW]:NVM:PFLASH_EDC_COMPARATOR
SM[HW]:NVM:PFLASH_ERROR_CORRECTION
SM[HW]:NVM:PFLASH_ERROR_MANAGEMENT
SM[HW]:NVM:PFLASH_WAIT_STATE_PROTECTION
SM[HW]:NVM:REG_MONITOR
SM[HW]:NVM:STARTUP_PROTECTION
In addition to the safety mechanisms mentioned in the first row.
- ReqIF-WF.Type: Requirement

##### RDVA-FJEE-DBCH-HDEE-003
If the AURIX™ TC4xx MCU features the NVMR functional block, then the system integrator shall ensure that the external safety mechanisms listed here are implemented and that the internal safety mechanisms listed here are configured and activated when using the TUC MCU boot:
SM[HW]:NVMR:MISR
SM[HW]:NVMR:BOOTROM_ADDR_PROTECTION
SM[HW]:NVMR:BOOTROM_ERROR_CORRECTION
SM[HW]:NVMR:PNVM_ECC_ONLINE_MONITOR
SM[HW]:NVMR:PNVM_ERROR_MANAGEMENT
SM[HW]:NVMR:PNVM_WAIT_STATE_PROTECTION
SM[HW]:NVMR:REG_MONITOR
SM[HW]:NVMR:STARTUP_PROTECTION
In addition to the safety mechanisms mentioned in the first row.
- ReqIF-WF.Type: Requirement

### QPGA-FJEJ-HGIB-DEFI: Redundant GPI channels
The MCU receives redundant signals from the system. There are so called 'mission channel' and 'monitoring channel' which respectively receives each input signal and processes it by independent PORT resources.
- Each signal is processed by one PORT input resource.
- Each signal processing result can be read by bus master (for example CPU, DMA).
- Simple digital signal like ON/OFF is considered in this TUC. Any sophisticated digital signal like PWM is NOT considered to be covered by this TUC.
- IFX.Version: 5
- ReqIF-WF.Type: Information

#### OSZA-FJEE-CHFD-IGGC: Specific assumptions of use
To make use of this tlsr use case, the system integrator shall ensure that the following assumptions of use are fulfilled:
- IFX.Version: 4
- ReqIF-WF.Type: Information

##### osz1605538649773-001
It is assumed that the system integrator chooses package pins with sufficient physical separation for each of the redundant GPI inputs.
See chapter Safety related information for package
- ReqIF-WF.Type: Requirement

#### DEFA-FJEE-DBAB-CFDD: Application diagram
The application diagram for this tlsr use case is shown below.
Application diagram for the tlsr use case Redundant GPI channels
- IFX.Version: 3
- ReqIF-WF.Type: Information

#### JQHA-FJEE-DBDB-IEHG: Internal and external safety mechanisms
For this use case, the following internal safety mechanisms are considered to be configured, activated and used in addition to those stated in Internal and external safety mechanisms. All external safety mechanisms mentioned below shall be provided by the system integrator.
- IFX.Version: 7
- ReqIF-WF.Type: Information

##### JQHA-FJEE-DBDB-IEHG-001
The system integrator shall implement the safety mechanisms listed here when using the TUC Redundant GPI channels:
ESM[SW]:PORTS:GPI_REDUNDANCY
SM[HW]:FPI:TRANSACTION_INTEGRITY
- ReqIF-WF.Type: Requirement

### ICCA-FJEJ-HGIA-AHIA: Redundant GPT12 channels
The MCU receives redundant signals from the system. There are so called 'mission channel' and 'monitoring channel' which respectively receives each digital input signal and processes it by redundant MCU timer resources.
- Each signal is processed by one GPT12 input resource, in turn, 2 GPT12 input resources are used.
- Each signal processing result can be read by bus master (for example CPU, DMA, PPU).
- Any sophisticated digital signal like PWM as well as simple digital signal like ON/OFF are considered in this TUC.
Note : Optionally, external digital signals can be filtered by GTM or eGTM before they are processed by GPT12.
- IFX.Version: 4
- ReqIF-WF.Type: Information

#### NWFA-FJEE-CHFD-CFAC: Specific assumptions of use
To make use of this tlsr use case, the system integrator shall ensure that the following assumptions of use are fulfilled:
- IFX.Version: 4
- ReqIF-WF.Type: Information

##### nwf1605538643613-001
It is assumed that the system integrator chooses package pins with sufficient physical separation for each of the redundant GPT12 inputs.
See chapter Safety related information for package
- ReqIF-WF.Type: Requirement

#### TPJA-FJEE-DBAA-FBJC: Application diagram
The application diagram for this tlsr use case is shown below.
Application diagram for the tlsr use case Redundant GPT12 channels
- IFX.Version: 3
- ReqIF-WF.Type: Information

#### YQYA-FJEE-DBDB-AJCJ: Internal and external safety mechanisms
For this use case, the following internal safety mechanisms are considered to be configured, activated and used in addition to those stated in Internal and external safety mechanisms. All external safety mechanisms mentioned below shall be provided by the system integrator.
- IFX.Version: 7
- ReqIF-WF.Type: Information

##### yqy1605542421030-001
The system integrator shall implement the safety mechanisms listed here when using the TUC Redundant GPT12 channels:
ESM[SW]:GPT12:ISR_MONITOR
ESM[SW]:GPT12:TIMER_REDUNDANCY
SM[HW]:FPI:TRANSACTION_INTEGRITY
- ReqIF-WF.Type: Requirement

### PHLA-FJEJ-HHBC-JEGG: Homogenous redundant ADC channels
- The MCU receives redundant signals from the external analog device(s). There are so called 'mission channel' and 'monitoring channel' which respectively receives each analog input signal and processes it by redundant but independent MCU resource.
- - Each analog input signal is processed by one ADC resource, in turn, 2 ADC resources are used.
- - Each analog input signal processing result can be read by bus master (for example CPU, DMA, PPU).
- - AURIX™ TC43x provides 3 different types of ADC function
- TMADC: Time Multiplexed ADC
- DSADC: Delta-Sigma ADC
- FCC: Fast Compare Cluster ADC
- In this Use Case, 3 ways of ADC redundancy are considered based on assumed application usage and expert's judgment.
- SUB1: TMADC + TMADC
- SUB2: DSADC + DSADC
- SUB3: FCC + FCC
- For SUB1 and SUB2 mentioned above, optionally CDSP, which is a hardware and software instance of 'Conversion Data Post-processing' function, can be used redundantly as well.
Note: SUB2 above also includes the usage of the DSADC external modulator (EXMOD) channel for voltage sensing.
- IFX.Version: 4
- ReqIF-WF.Type: Information

#### CKWA-FJEE-CHFF-AIJA: Specific assumptions of use
To make use of this tlsr use case, the system integrator shall ensure that the following assumptions of use are fulfilled:
- IFX.Version: 4
- ReqIF-WF.Type: Information

##### ckw1605538661901-001
It is assumed that the system integrator chooses package pins with sufficient physical separation for each of the redundant ADC inputs.
See chapter Safety related information for package
- ReqIF-WF.Type: Requirement

#### OUPA-FJEE-DBAF-BDJA: Application diagram
The application diagram for this tlsr use case is shown below.
Application diagram for the tlsr use case Homogenous redundant ADC channels
- IFX.Version: 3
- ReqIF-WF.Type: Information

#### ZCOA-FJEE-DBDD-FCFH: Internal and external safety mechanisms
For this use case, the following internal safety mechanisms are considered to be configured, activated and used in addition to those stated in Internal and external safety mechanisms. All external safety mechanisms mentioned below shall be provided by the system integrator.
- IFX.Version: 10
- ReqIF-WF.Type: Information

##### ZCOA-FJEE-DBDD-FCFH-001
The system integrator shall implement the safety mechanisms listed here when using the TUC Homogenous redundant ADC channels:
ESM[SW]:ADC:CONFIG_READBACK
ESM[SW]:ADC:ISR_MONITOR
ESM[SW]:ADC:MODULE_REDUNDANCY
ESM[SW]:ADC:RESULT_PLAUSIBILITY
ESM[SW]:ADC:VAREF_PLAUSIBILITY
SM[HW]:ADC:RESULT_PLAUSIBILITY
SM[HW]:FPI:TRANSACTION_INTEGRITY
- ReqIF-WF.Type: Requirement

### WASA-FJEJ-HHCG-AAGF: Single input redundant ADC channels
- The MCU receives a single signal from the external analog device. There are so called 'mission channel' ADC and 'monitoring channel' ADC which receive the same analog input signal but independently process the analog signal by 2 redundant ADC functions.
- Single pin is shared(multiplexed) between redundant ADC modules, in turn, 2 ADC resources are used.
- Each ADC processes the signal and processing result can be read by bus master (for example CPU, DMA, PPU).
- AURIX™ TC43x provides 3 different types of ADC function
- TMADC: Time Multiplexed ADC
- DSADC: Delta-Sigma ADC
- FCC: Fast Compare Cluster ADC
- In this TUC, 3 different types of ADC sharing feature are considered.
1. Sharing between 2 TMADC modules to provide homogeneous redundancy (CDSP, which is a hardware and software instance of 'Conversion Data Post-processing' function, can be used optionally.)
2. Sharing between TMADC module and DSADC module to provide heterogeneous redundancy (CDSP, which is a hardware and software instance of 'Conversion Data Post-processing' function, can be used optionally.)
3. Sharing between TMADC module and FCC module to provide heterogeneous redundancy
Note 1: Sharing between DSADC and FCC is NOT considered in this TUC as there is no reliable safety mechanism to detect the common cause failure caused by the shared input pin failure.
Note 2: Not all ADC Pins are shared between redundant ADC modules.
- IFX.Version: 4
- ReqIF-WF.Type: Information

#### VQEA-FJEE-CHGC-FBAH: Specific assumptions of use
There are no specific assumptions of use for this use case.
- IFX.Version: 3
- ReqIF-WF.Type: Information

#### RFTA-FJEE-DBBE-AJJA: Application diagram
The application diagram for this tlsr use case is shown below.
Application diagram for the tlsr use case Single input redundant ADC channels
- IFX.Version: 3
- ReqIF-WF.Type: Information

#### OYDA-FJEE-DBEB-BAIC: Internal and external safety mechanisms
For this use case, the following Internal safety mechanisms are considered to be configured, activated and used in addition to those stated in Internal and external safety mechanisms. All external safety mechanisms mentioned below shall be provided by the system integrator.
- IFX.Version: 10
- ReqIF-WF.Type: Information

##### OYDA-FJEE-DBEB-BAIC-001
The system integrator shall implement the safety mechanisms listed here when using the TUC Single input redundant ADC channels:
ESM[SW]:ADC:BROKEN_WIRE_DETECTION
ESM[SW]:ADC:CONFIG_READBACK
ESM[SW]:ADC:ISR_MONITOR
ESM[SW]:ADC:MODULE_REDUNDANCY
ESM[SW]:ADC:RESULT_PLAUSIBILITY
ESM[SW]:ADC:VAREF_PLAUSIBILITY
SM[HW]:ADC:RESULT_PLAUSIBILITY
SM[HW]:FPI:TRANSACTION_INTEGRITY
- ReqIF-WF.Type: Requirement

### AHKA-FEHG-DHIH-AHBG: GPT12 output
This TUC is considering the scenario where the GPT12 is being used to generate a digital control signal for an external actuator. The signal could be a simple on or off, or time changing like a pulse width modulation (PWM) signal.
The output signal properties (for example frequency, duty cycle, etc.) are calculated by the application software in the TriCore™ CPU and then, as shown in the application diagram below, forwarded through the FPI bus to the GPT12. At the same time the application software keeps a local copy in an ASIL memory of the control signal properties. The GPT12 then generates the control signal which goes through the PORTS and the package of the AURIX™ TC4xx MCU and reaches the control input of the external actuator. This is the so-called Mission channel.
The external actuator provides a feedback signal that is correlated to the control signal received from the mission channel. This feedback signal is then fed into the so-called Monitoring channel by going through the package and PORTS into an input resource of the GPT12. The GPT12 then calculates the properties of the feedback signal which are then read by the TriCore™ CPU through the FPI bus. The application software can then detect a failure by comparing the properties of the feedback signal with the ones of the control signal stored previously in memory.
Note: for the Monitoring channel it is possible to use a resource of eGTM or GTM instead, if these are available. For more details, please refer to the TUCs eGTM output and GTM output.
The input resource of the GPT12 can send an interrupt request to the interrupt router (IR), for example to signal availability of signal data. However, interrupt generation of the Monitoring channel is not considered to affect the control signal generation; this is rather a multi-point fault (MPF).
Note: there is an intrinsic delay from the point in time in which the control signal is provided to the external actuator until a potential fault is detected by the application software and a reaction can be triggered. The external actuator must therefore be capable of tolerating a wrong control signal for this period of time.
Common cause failure initiators
The potential Common Cause Failure initiators (CCFI) can affect both the mission and the monitoring logic simultaneously. Such a situation could lead to a violation of the safety goal. The table below shows the CCFI that are relevant for this TUC and the countermeasures that shall be applied to mitigate them:
| CCFI | Associated functional block | TUC addressing this CCFI |
| --- | --- | --- |
| Clock | CLOCK | Common cause failure by clock |
| Power | PMS | Common cause failure by power |
| Reset | SMM | Common cause failure by system management |
| product configuration | SCU | Common cause failure by system management |
| Logic test | TRI | Common cause failure by Test and Debug functions |
| Memory Test | VMT | Common cause failure by Test and Debug functions |
| Debug | Debug and trace | Common cause failure by Test and Debug functions |
- IFX.Version: 2
- ReqIF-WF.Type: Information

#### HXJA-FEHG-DIJD-HGBB: Specific assumptions of use
There are no specific assumptions of use for this use case.
- IFX.Version: 2
- ReqIF-WF.Type: Information

#### TIWA-FEHG-DIJE-IHFE: Application diagram
The application diagram below shows the functional blocks and interfaces involved in this tlsr use case. This TUC derives safety measures for those functional blocks and interfaces that are shown in colors. This TUC does not address the safety integrity of the functional blocks and interfaces shown in Black or Grey. In particular:
- The TriCore™ CPU plays a role in this TUC for example by performing the computations necessary to provide the control signal and comparing it with the feedback signal. However, the safety integrity of these operations is addressed in the TUCs under the top level safety requirement "Safe software execution platform [ASIL D]"
- The interrupt router is used for handling the interrupt requests originating from the functional blocks involved in this TUC and interrupt service requests going to the CPU. The safety integrity of the interrupt handling is addressed in the TUC Interrupts
Application diagram for the TUC GPT12 output
- IFX.Version: 2
- ReqIF-WF.Type: Information

#### YFAA-FEHG-EJAJ-IEBJ: Internal and external safety mechanisms
For this use case, the following internal safety mechanisms are considered to be configured, activated and used in addition to those stated in Internal and external safety mechanisms. All external safety mechanisms mentioned below shall be provided by the system integrator.
- IFX.Version: 3
- ReqIF-WF.Type: Information

##### yfa1658750109520-001
The system integrator shall ensure that the external safety mechanisms listed here are implemented and that the internal safety mechanisms listed here are configured and activated when using the TUC GPT12 output:
ESM[SW]:GPT12:OUTPUT_MONITORING
SM[HW]:FPI:TRANSACTION_INTEGRITY
- ReqIF-WF.Type: Requirement

### XIBA-FJEJ-HHBI-IDEH: GPO Output Read-Back
The MCU sends a digital output signal through a PORT output resource to activate the external actuator or device (for example a relay, switch, etc.) and receives a feedback signal through another PORT input resource that correlates with the generated output signal.
- Mission channel: digital output signal is generated by PORT output resource.
- Monitoring channel: the MCU receives feedback signal(s) from the external actuator or device through PORT input resource.
- Only simple digital output signal like ON/OFF is considered in this TUC. The safety integrity of any sophisticated digital output signals like PWM is considered in eGTM output and GTM output TUCs.
- IFX.Version: 5
- ReqIF-WF.Type: Information

#### XDUA-FJEE-CHFI-HHGD: Specific assumptions of use
There are no specific assumptions of use for this use case.
- IFX.Version: 3
- ReqIF-WF.Type: Information

#### RRVA-FJEE-DBBA-BFIJ: Application diagram
The application diagram for this tlsr use case is shown below.
Application diagram for the tlsr use case GPO output read-back
- IFX.Version: 4
- ReqIF-WF.Type: Information

#### JJTA-FJEE-DBDH-JJGH: Internal and external safety mechanisms
For this use case, the following internal safety mechanisms are considered to be configured, activated and used in addition to those stated in Internal and external safety mechanisms. All external safety mechanisms mentioned below shall be provided by the system integrator.
- IFX.Version: 7
- ReqIF-WF.Type: Information

##### JJTA-FJEE-DBDH-JJGH-001
The system integrator shall implement the safety mechanisms listed here when using the TUC GPO Output Read-Back:
ESM[SW]:PORTS:GPO_READBACK
SM[HW]:FPI:TRANSACTION_INTEGRITY
- ReqIF-WF.Type: Requirement

### PXRA-EIAF-IEBE-JHCF: Single communication channel
This chapter describes in detail the TUC "Single communication channel" and provides all the use case specific information that are not already provided in Common for all use cases.
The MCU establishes the communication with external party. The message or data is exchanged between the Sender and the Receiver who are capable of executing sophisticated software execution like encoding and decoding of cyclic redundancy check, generation and confirmation of time stamp, etc.
This TUC has the following sub use cases:
- SUB1 - Single channel GETH/LETH communication
- SUB2 - Single channel PCIe communication
- SUB3 - Single channel CAN/CANXL communication
- SUB4 - Single channel ERAY communication
- SUB5 - Single channel HSSL communication
- SUB6 - Single channel SPI communication
- SUB7 - Single channel I2C communication
- SUB8 - Single channel ASCLIN communication
Note: some of the functional blocks listed above might not be available in a particular AURIX™ TC4xx device. Please refer to the "Device feature set" chapter in the Datasheet for more details.
- IFX.Version: 7
- ReqIF-WF.Type: Information

#### GTWA-FJJA-GGFH-DIHE: Specific assumptions of use
To make use of this tlsr use case, the system integrator shall ensure that the following assumptions of use are fulfilled:
Assumptions of use for the TUC
Single communication channel
| Type | Description | Comment |
| --- | --- | --- |
- IFX.Version: 6
- ReqIF-WF.Type: Information

##### gtw1600177684985-001
Any combination of above SUB use cases (for example MCAN receive and ERAY transmit) is NOT considered in this TUC.
- ReqIF-WF.Type: Requirement

##### gtw1600177684985-002
This TUC is only valid under the assumption that the external communication endpoint is able to handle sophisticated software tasks like safe end-to-end communication which consists of flexible CRC generation and calculation, attachment and checking of frame counter and time stamp, checking of message ID, etc. Typical use case is the communication between ECUs or MCUs.
- ReqIF-WF.Type: Requirement

##### gtw1600177684985-003
It is assumed that the external communication endpoint is able to handle the same safe end-to-end communication methods applied to MCU
- ReqIF-WF.Type: Requirement

##### gtw1600177684985-004
It is assumed that a failure of transmitted frame from AURIX™ TC43x is monitored by safe end-to-end communication methods at the external communication End Point
- ReqIF-WF.Type: Requirement

##### gtw1600177684985-005
The safety integrity of the FB(s) between each communication FB and PACKAGE during the external communication is ensured by communication protocol or safe end-to-end communication.
Example: a failure mode of HSPHY and PORT during GETH communication is monitored by ETH protocol or ETH safe end-to-end communication methods.
- ReqIF-WF.Type: Requirement

#### HGUA-EIAF-IEHH-HJGF: Application diagram
The application diagram for this tlsr use case is shown below.
Application diagram for the tlsr use case Single communication channel
- IFX.Version: 7
- ReqIF-WF.Type: Information

#### KQCA-FJJA-GGGB-HJDI: Internal and external safety mechanisms
For this use case, the following internal safety mechanisms are considered to be configured, activated and used in addition to those stated in Internal and external safety mechanisms. All external safety mechanisms mentioned below shall be provided by the system integrator.
- IFX.Version: 19
- ReqIF-WF.Type: Information

##### KQCA-FJJA-GGGB-HJDI-001
The system integrator shall ensure that the external safety mechanisms listed here are implemented and that the internal safety mechanisms listed here are configured and activated IF the functional block asynchronous synchronous interface is used for the TUC Single communication channel
ESM[SW]:ASCLIN:SAFE_COMMUNICATION
ESM[SW]:ASCLIN:ISR_MONITOR
SM[HW]:FPI:TRANSACTION_INTEGRITY
ESM[SW]:SMU:ALARM_SIGNAL_TEST
- ReqIF-WF.Type: Requirement

##### KQCA-FJJA-GGGB-HJDI-002
The system integrator shall ensure that the external safety mechanisms listed here are implemented and that the internal safety mechanisms listed here are configured and activated IF the functional block Flexray is used for the TUC Single communication channel
ESM[SW]:ERAY:SAFE_COMMUNICATION
ESM[SW]:ERAY:ISR_MONITOR
ESM[SW]:SMU:ALARM_SIGNAL_TEST
SM[HW]:FPI:TRANSACTION_INTEGRITY
SM[HW]:FB:ERROR_CORRECTION
SM[HW]:FB:ECC_MONITOR
SM[HW]:FB:ADDRESS
SM[HW]:FB:MBIST
SM[HW]:FB:CONTROL
SM[HW]:FB:SM_CONTROL
- ReqIF-WF.Type: Requirement

##### KQCA-FJJA-GGGB-HJDI-003
The system integrator shall ensure that the external safety mechanisms listed here are implemented and that the internal safety mechanisms listed here are configured and activated IF the functional block Gigabit ethernet is used for the TUC Single communication channel
ESM[SW]:GETH:SAFE_COMMUNICATION
ESM[SW]:GETH:ISR_MONITOR
ESM[SW]:SMU:ALARM_SIGNAL_TEST
SM[HW]:HSPHY:REG_MONITOR
SM[HW]:FPI:TRANSACTION_INTEGRITY
SM[HW]:SRI:SRI_TRANSACTION_INTEGRITY
SM[HW]:FB:ERROR_CORRECTION
SM[HW]:FB:ECC_MONITOR
SM[HW]:FB:ADDRESS
SM[HW]:FB:MBIST
SM[HW]:FB:CONTROL
SM[HW]:FB:SM_CONTROL
SM[HW]:FB:ADDRESS
SM[HW]:FB:MBIST
SM[HW]:FB:CONTROL
SM[HW]:FB:SM_CONTROL
- ReqIF-WF.Type: Requirement

##### KQCA-FJJA-GGGB-HJDI-004
The system integrator shall ensure that the external safety mechanisms listed here are implemented and that the internal safety mechanisms listed here are configured and activated IF the functional block Lite Ethernet (LETH) is used for the TUC Single communication channel
ESM[SW]:LETH:SAFE_COMMUNICATION
ESM[SW]:LETH:ISR_MONITOR
SM[HW]:FB:ERROR_CORRECTION
SM[HW]:FB:ECC_MONITOR
SM[HW]:FB:ADDRESS
SM[HW]:FB:MBIST
SM[HW]:FB:CONTROL
SM[HW]:FB:SM_CONTROL
SM[HW]:SRI:SRI_TRANSACTION_INTEGRITY
- ReqIF-WF.Type: Requirement

##### KQCA-FJJA-GGGB-HJDI-005
The system integrator shall ensure that the external safety mechanisms listed here are implemented and that the internal safety mechanisms listed here are configured and activated IF the functional block high speed serial link is used for the TUC Single communication channel
ESM[SW]:HSSL:SAFE_COMMUNICATION
ESM[SW]:HSSL:ISR_MONITOR
SM[HW]:FPI:TRANSACTION_INTEGRITY
SM[HW]:SRI:SRI_TRANSACTION_INTEGRITY
- ReqIF-WF.Type: Requirement

##### KQCA-FJJA-GGGB-HJDI-006
The system integrator shall ensure that the external safety mechanisms listed here are implemented and that the internal safety mechanisms listed here are configured and activated IF the functional block Inter-Integrated circuit is used for the TUC Single communication channel
ESM[SW]:I2C:ISR_MONITOR
ESM[SW]:I2C:SAFE_COMMUNICATION
SM[HW]:FPI:TRANSACTION_INTEGRITY
- ReqIF-WF.Type: Requirement

##### KQCA-FJJA-GGGB-HJDI-007
The system integrator shall ensure that the external safety mechanisms listed here are implemented and that the internal safety mechanisms listed here are configured and activated IF the functional block controller area network is used for the TUC Single communication channel
ESM[SW]:CAN:SAFE_COMMUNICATION
ESM[SW]:CAN:ISR_MONITOR
SM[HW]:FPI:TRANSACTION_INTEGRITY
SM[HW]:FB:ERROR_CORRECTION
SM[HW]:FB:ECC_MONITOR
SM[HW]:FB:ADDRESS
SM[HW]:FB:MBIST
SM[HW]:FB:CONTROL
SM[HW]:FB:SM_CONTROL
- ReqIF-WF.Type: Requirement

##### KQCA-FJJA-GGGB-HJDI-008
The system integrator shall ensure that the external safety mechanisms listed here are implemented and that the internal safety mechanisms listed here are configured and activated IF the functional block CANXL is used for the TUC Single communication channel
ESM[SW]:CANXL:ISR_MONITOR
ESM[SW]:CANXL:SAFE_COMMUNICATION
SM[HW]:FPI:TRANSACTION_INTEGRITY
SM[HW]:FB:ERROR_CORRECTION
SM[HW]:FB:ECC_MONITOR
SM[HW]:FB:ADDRESS
SM[HW]:FB:MBIST
SM[HW]:FB:CONTROL
SM[HW]:FB:SM_CONTROL
- ReqIF-WF.Type: Requirement

##### KQCA-FJJA-GGGB-HJDI-009
The system integrator shall ensure that the external safety mechanisms listed here are implemented and that the internal safety mechanisms listed here are configured and activated IF the functional block peripheral component interconnect express is used for the TUC Single communication channel
ESM[SW]:PCIE:SAFE_COMMUNICATION
ESM[SW]:PCIE:ISR_MONITOR
ESM[SW]:SMU:ALARM_SIGNAL_TEST
SM[HW]:HSPHY:REG_MONITOR
SM[HW]:FPI:TRANSACTION_INTEGRITY
SM[HW]:FB:ADDRESS
SM[HW]:FB:MBIST
SM[HW]:FB:CONTROL
SM[HW]:FB:SM_CONTROL
SM[HW]:FB:ADDRESS
SM[HW]:FB:MBIST
SM[HW]:FB:CONTROL
SM[HW]:FB:SM_CONTROL
SM[HW]:SRI:SRI_TRANSACTION_INTEGRITY
- ReqIF-WF.Type: Requirement

##### KQCA-FJJA-GGGB-HJDI-010
The system integrator shall ensure that the external safety mechanisms listed here are implemented and that the internal safety mechanisms listed here are configured and activated IF the functional block queued synchronous peripheral interface is used for the TUC Single communication channel
ESM[SW]:QSPI:SAFE_COMMUNICATION
ESM[SW]:QSPI:ISR_MONITOR
ESM[SW]:SMU:ALARM_SIGNAL_TEST
SM[HW]:FPI:TRANSACTION_INTEGRITY
- ReqIF-WF.Type: Requirement

### NNFA-FJEJ-HHCD-CHIB: Redundant communication channels
The MCU establishes the communication with external party. The message or data is exchanged between the Sender and the Receiver who are NOT capable of executing sophisticated software execution like encoding and decoding of CRC, generation and confirmation of time stamp, etc.
This TUC has the following sub use cases:
- SUB1 - Redundant SPI communication
- SUB2 - Redundant I2C communication
- SUB3 - Redundant ASCLIN communication
Note: Heterogeneous redundancy is possible for cases below based on application usage:
1. ASCLIN(UART) with I2C
2. ASCLIN(SPI) with QSPI (limitation: master function only. ASCLIN doesn't support slave mode)
- IFX.Version: 5
- ReqIF-WF.Type: Information

#### BUTA-FJEE-CHGB-BDJJ: Specific assumptions of use
To make use of this tlsr use case, the system integrator shall ensure that the following assumptions of use are fulfilled:
- IFX.Version: 6
- ReqIF-WF.Type: Information

##### but1605538722400-001
This tlsr use case is only valid under the assumption that the external party is capable of responding to transmitted frames from the MCU, for example Transmit/Verify method.
Note: The safety integrity of the transmitted frame of the MCU can only be verified by the received party.
- ReqIF-WF.Type: Requirement

#### WLTA-FJEE-DBBC-FJDG: Application diagram
The application diagram for this tlsr use case is shown below.
Application diagram for the tlsr use case Redundant communication channels
- IFX.Version: 4
- ReqIF-WF.Type: Information

#### IAHA-FJEE-DBEJ-FJJH: Internal and external safety mechanisms
For this use case, the following internal safety mechanisms are considered to be configured, activated and used in addition to those stated in Internal and external safety mechanisms. All external safety mechanisms mentioned below shall be provided by the system integrator.
- IFX.Version: 11
- ReqIF-WF.Type: Information

##### IAHA-FJEE-DBEJ-FJJH-001
The system integrator shall implement the safety mechanisms listed here when using the asynchronous synchronous interface module for the TUC Redundant communication channels:
ESM[SW]:ASCLIN:CHANNEL_REDUNDANCY
- ReqIF-WF.Type: Requirement

##### IAHA-FJEE-DBEJ-FJJH-002
The system integrator shall implement the safety mechanisms listed here when using the Inter-Integrated circuit module for the TUC Redundant communication channels:
ESM[SW]:I2C:CHANNEL_REDUNDANCY
- ReqIF-WF.Type: Requirement

##### IAHA-FJEE-DBEJ-FJJH-003
The system integrator shall implement the safety mechanisms listed here when using the queued synchronous peripheral interface module for the TUC Redundant communication channels:
ESM[SW]:QSPI:CHANNEL_REDUNDANCY
- ReqIF-WF.Type: Requirement

### FXIA-FJEJ-HHCE-CCCB: External device configuration
The MCU establishes the communication with a external device in order to configure the external device or read the status of the external device.
Note: In this TUC, the MCU is assumed to be always the master of the communication.
The following communication peripherals are considered in this TUC (exhaustive list):
- QSPI
- IFX.Version: 3
- ReqIF-WF.Type: Information

#### CWMA-FJEE-CHGB-IFJI: Specific assumptions of use
To make use of this tlsr use case, the system integrator shall ensure that the following assumptions of use are fulfilled:
- IFX.Version: 5
- ReqIF-WF.Type: Information

##### cwm1605538729609-001
It is assumed that the MCU is always the master of the communication.
- ReqIF-WF.Type: Requirement

#### CWJA-FJEE-DBBD-CBFE: Application diagram
The application diagram for this tlsr use case is shown below.
Application diagram for the tlsr use case External device configuration
- IFX.Version: 3
- ReqIF-WF.Type: Information

#### UOOA-FJEE-DBEA-CIAD: Internal and external safety mechanisms
For this use case, the following internal safety mechanisms are considered to be configured, activated and used in addition to those stated in Internal and external safety mechanisms. All external safety mechanisms mentioned below shall be provided by the system integrator.
- IFX.Version: 8
- ReqIF-WF.Type: Information

##### UOOA-FJEE-DBEA-CIAD-001
The system integrator shall implement the safety mechanisms listed here when using the TUC External device configuration:
ESM[SW]:QSPI:ISR_MONITOR
ESM[SW]:QSPI:SAFE_DEVICE_CONFIGURATION
ESM[SW]:SMU:ALARM_SIGNAL_TEST
SM[HW]:FPI:TRANSACTION_INTEGRITY
- ReqIF-WF.Type: Requirement

### KYNA-FEHG-CIHD-EFEA: Radar input processing
This TUC is considering the scenario where the radar interface (RIF) is being used to acquire radar data from an external radar device like for example a monolithic microwave integrated circuit (MMIC).
As shown in the application diagram below, the data originating from the external radar device goes through the microcontroller unit pins, package and PORTS into the RIF. The RIF then converts the data into a compatible format and forwards it to the signal processing unit (SPU) or alternatively to MCU memory through the SRI bus.
Note: As an option, the MCU can send synchronization signals from the power management system (PMS) to an external regulator in sync master mode, or receive synchronization signals from an external regulator in sync slave mode, in order to synchronize the frequency and the phase between the internal voltage regulator and an external one. Incorrect synchronization may affect RIF inputs in such a way that it can result in ghost objects or missing objects.
The SPU then receives the data and performs the radar data processing (for example range or velocity estimation). Afterwards, this the data is stored in the radar memory (RMEM) which can be accessed by the radar direct memory access (RDMA) through a dedicated interface or by any other MCU master function through the SRI bus. Alternatively, the SPU can provide the processed data directly to the MCU through the SRI interface.
The RDMA can then be used to move the radar data from one location to another, for example for post-processing. However, post-processing of radar data is not considered in this TUC. RDMA data movement can be triggered by internal RDMA configuration or by an interrupt service request coming from the interrupt router (IR).
As shown in the application diagram below, the global system time-stamp unit (GST) is available as an option to receive synchronization information from a master ECU. The information is channeled through a communication interface (for example LETH or CAN) into the GST. The GST can then send synchronization triggers to the interrupt router (IR) or to an external device through PORTS. The GST can also be used as the master that sends synchronization information to other slave ECUs.
The RIF, SPU and RDMA can send interrupt requests to the IR for example to notify completion of events.
Common cause failure initiators
The potential Common Cause Failure initiators (CCFI) can affect both the mission and the monitoring logic simultaneously. Such a situation could lead to a violation of the safety goal. The table below shows the CCFI that are relevant for this TUC and the countermeasures that shall be applied to mitigate them:
| CCFI | Associated functional block | TUC addressing this CCFI |
| --- | --- | --- |
| Clock | CLOCK | Common cause failure by clock |
| Power | PMS | Common cause failure by power |
| Reset | SMM | Common cause failure by system management |
| product configuration | SCU | Common cause failure by system management |
| Logic test | TRI | Common cause failure by Test and Debug functions |
| Memory Test | VMT | Common cause failure by Test and Debug functions |
| Debug | Debug and trace | Common cause failure by Test and Debug functions |
- IFX.Version: 2
- ReqIF-WF.Type: Information

#### AQLA-FEHG-CIIA-EDDD: Specific assumptions of use
To make use of this tlsr use case, the system integrator shall ensure that the following assumptions of use are fulfilled:
Assumptions of use for the TUC
Radar input processing
| Type | Description | Comment |
| --- | --- | --- |
- IFX.Version: 3
- ReqIF-WF.Type: Information

##### aql1658739915444-001
It is assumed that the interface(s) of the external radar device providing the radar data is (are) compatible at the physical layer (voltage, polarity, etc.) with the radar interface (RIF) of the AURIX™ TC4xx radar MCU.
- ReqIF-WF.Type: Requirement

#### JTRA-FEHG-CIIG-EHJD: Application diagram
The application diagram below shows the functional blocks and interfaces involved in this tlsr use case. This TUC derives safety measures for those functional blocks and interfaces that are shown in colors. This TUC does not address the safety integrity of the functional blocks and interfaces shown in Black or Grey. In particular:
- The TriCore™ CPU plays a role in this TUC for example by writing the configuration registers of the functional blocks involved in this TUC. However the safety integrity of these operations is addressed in the TUCs under the TLSR “Safe software execution platform [ASIL D]”
- The interrupt router is used for handling the interrupt requests originating from the functional blocks involved in this TUC and interrupt service requests going to the RDMA. The safety integrity of the interrupt handling is addressed in the TUC Interrupts
- For radar devices that feature the parallel processing unit co-processor, it can be used for radar data post-processing. Safety integrity of radar data post-processing with the PPU is covered by the TUC Parallel processing for radar data
- The GPT12 and PMS can be used for synchronization with an external power supply. Safety integrity of this optional function is covered by PMS
Application diagram for the TUC Radar input processing
- IFX.Version: 2
- ReqIF-WF.Type: Information

#### VTMA-FEHG-DJJJ-FCBF: Internal and external safety mechanisms
For this use case, the following internal safety mechanisms are considered to be configured, activated and used in addition to those stated in Internal and external safety mechanisms. All external safety mechanisms mentioned below shall be provided by the system integrator.
- IFX.Version: 3
- ReqIF-WF.Type: Information

##### vtm1658740006326-001
The system integrator shall ensure that the external safety mechanisms listed here are implemented and that the internal safety mechanisms listed here are configured and activated when using the TUC Radar input processing:
ESM[SW]:RIF:CSI-2_ERROR_HANDLING
ESM[SW]:RIF:ERROR_HANDLING
ESM[SW]:RIF:ISR_MONITOR
ESM[SW]:SPU:CONTROL_FLOW_SIGNATURE
ESM[SW]:SPU:DATA_INTEGRITY
ESM[SW]:SPU:EXECUTION_TIME_CHECK
ESM[SW]:SPU:ISR_MONITOR
ESM[SW]:SPU:SBST
ESM[SW]:SPU:SM_CHECK
SM[HW]:FPI:TRANSACTION_INTEGRITY
SM[HW]:RIF:ACTIVE_CFG_CHECK
SM[HW]:RIF:ACTIVE_CFG_CHECK_SCC
SM[HW]:RIF:CONTROL_REDUNDANCY
SM[HW]:RIF:ERROR_HANDLING
SM[HW]:RIF:TEMPORAL_MONITOR
SM[HW]:RMEM:CONTROL_REDUNDNACY
SM[HW]:SPU:READ_WRITE_ECC
SM[HW]:RMEM:SEP_TRANSACTION_INTEGRITY
SM[HW]:SPU:ACTIVE_CONFIG_CHECK
SM[HW]:SPU:ACTIVE_CONFIG_CHECK_SCC
SM[HW]:SPU:CONTROL_FLOW_SIGNATURE
SM[HW]:SPU:CONTROL_REDUNDANCY
SM[HW]:SPU:CONTROL_REDUNDANCY_SCC
SM[HW]:SPU:DATA_PROTECTION
SM[HW]:SPU:RIF_INTERFACE
SM[HW]:SPU:SEP_TRANSACTION_INTEGRITY
SM[HW]:SPU:SM_CHECK
SM[HW]:FB:ERROR_CORRECTION
SM[HW]:FB:ECC_MONITOR
SM[HW]:FB:ADDRESS
SM[HW]:SRI:SRI_TRANSACTION_INTEGRITY
SM[HW]:WTU:TEMPORAL_MONITORING
SM[HW]:RIF:PARITY_CHECK
SM[SW]:SPU:SBST
- ReqIF-WF.Type: Requirement

##### vtm1658740006326-002
The system integrator shall ensure that the external safety mechanisms listed here are implemented and that the internal safety mechanisms listed here are configured and activated IF RDMA is used in the context of the TUC Radar input processing:
ESM[SW]:RDMA:ISR_MONITOR
ESM[SW]:SMU:ALARM_SIGNAL_TEST
SM[HW]:RDMA:ACTIVE_CFG_CHECK
SM[HW]:RDMA:ACTIVE_CFG_CHECK_SCC
SM[HW]:RDMA:REDUNDANCY
SM[HW]:RDMA:REDUNDANCY_SCC
SM[HW]:RDMA:SEP_TRANSACTION_INTEGRITY
SM[HW]:FB:ERROR_CORRECTION
SM[HW]:FB:ECC_MONITOR
SM[HW]:FB:ADDRESS
SM[HW]:FB:MBIST
SM[HW]:FB:CONTROL
SM[HW]:FB:SM_CONTROL
SM[HW]:IR:ICU_MONITOR
To be used in addition to the safety mechanisms mentioned in the first row
- ReqIF-WF.Type: Requirement

##### vtm1658740006326-003
The system integrator shall ensure that the external safety mechanisms listed here are implemented and that the internal safety mechanisms listed here are configured and activated when using the TUC Radar input processing IF the GST is used for ECU synchronization:
ESM[SW]:GST:CONFIG_READBACK
ESM[SW]:GST:ISR_MONITOR
ESM[SW]:LETH:ISR_MONITOR
SM[HW]:GST:REG_MONITOR
To be used in addition to the safety mechanisms mentioned in the first row
- ReqIF-WF.Type: Requirement

##### vtm1658740006326-004
The system integrator shall ensure that the external safety mechanisms listed here are implemented and that the internal safety mechanisms listed here are configured and activated IF the power supply synchronization feature is used in the context of the TUC Radar input processing:
SM[HW]:PMS:SYNC_MONITOR
To be used in addition to the ones mentioned in the first row
- ReqIF-WF.Type: Requirement

### VFHA-FJGF-GCJJ-BDIF: Cyber-security message authentication
This TUC considers the scenario where the MCU receives a cyber-security relevant message through one of its communication interfaces (CAN or ETH). The MCU then verifies the message authentication code (MAC) of the message received (for example from another ECU) that was appended by the sender.
Note: Any security breach is considered as interference to safety-related hardware and software elements.
The main goal of this TUC is to prevent a 'false positive' message verification, that is, to avoid the acceptance of an unauthorized message.
Note: The MAC is included in a message of the CAN or ETH communication. The safety integrity of the CAN or ETH message frame is not part of this TUC; it is addressed by the TUC Single communication channel.
- IFX.Version: 4
- ReqIF-WF.Type: Information

#### LSDA-FDCB-JGFI-FEEC: Specific assumptions of use
To make use of this tlsr use case, the system integrator shall ensure that the following assumptions of use are fulfilled:
- IFX.Version: 3
- ReqIF-WF.Type: Information

##### lsd1643207696553-001
It is assumed that a failure of the transmitted message from the AURIX™ TC4xx microcontroller is monitored by the external communication End Point.
- ReqIF-WF.Type: Requirement

#### GUCA-FDCB-JGGA-CFGD: Application diagram
The application diagram for this tlsr use case is shown below.
Application diagram for the tlsr use case Cyber-security message authentication
APPLICATION DIAGRAM UNDER CONSTRUCTION
- IFX.Version: 2
- ReqIF-WF.Type: Information

#### UCYA-FDCA-ADFB-AAJI: Internal and external safety mechanisms
For this use case, the following internal safety mechanisms are considered to be configured, activated and used in addition to those stated in Internal and external safety mechanisms. All external safety mechanisms mentioned below shall be provided by the system integrator.
- IFX.Version: 4
- ReqIF-WF.Type: Information

##### UCYA-FDCA-ADFB-AAJI-001
The system integrator shall implement the safety mechanisms listed here when using the TUC Cyber-security message authentication:
ESM[SW]:SMU:ALARM_SIGNAL_TEST
ESM[SW]:CSS:FUNCTIONAL_MONITORING
ESM[SW]:CSS:ISR_MONITOR
SM[HW]:CSS:REG_MONITOR
SM[HW]:CSS:SAFE_MAC_COMP
SM[HW]:FB:ERROR_CORRECTION
SM[HW]:SRI:SRI_TRANSACTION_INTEGRITY
- ReqIF-WF.Type: Requirement

### DGMA-FCCJ-GAAH-AECG: Systematic fault avoidance
All hardware in the AURIX™ TC4xx microcontroller unit family has been developed to ensure avoidance of systematic faults in the hardware in compliance to the ISO 26262:2018 requirements for ASIL D with the following exceptions:
| Hardware part | Belongs to functional block | ASIL claim systematic fault avoidance in the hardware | Safety concept argumentation |
| --- | --- | --- | --- |
| Random number generator RNG | CSRM | QM | CSRM is not part of any MCU safety-related function |
| PKC accelerator | CSRM | QM | CSRM is not part of any MCU safety-related function |
| ERAY | ERAY | QM | Systematic faults in the hardware are covered by ESM[SW]:ERAY:SAFE_COMMUNICATION |
| CAN | CAN | QM | Systematic faults in the hardware are covered by ESM[SW]:CAN:SAFE_COMMUNICATION |
| XC800 core | SCR | QM | SCR is not part of any MCU safety-related function |
- IFX.Version: 4
- ReqIF-WF.Type: Information

### QULA-FJEJ-HHFB-FHFJ: Internal failure reporting interface
- Any failure detected by:
- 1) the hardware safety mechanism of the MCU or
- 2) the software safety mechanism of the MCU or
- 3) the system integrator's safety mechanism
can be notified to the system integrator by the SMU.
- Internal Failure Reporting Interface is an ability of the MCU Safe State Support architecture to enable hardware or software safety mechanisms to communicate with the system integrator's software for the purpose of indicating the presence of a failure.
- The Internal Failure Reporting Interface indicates two states:
- 1) MCU_FAULT_STATE: the state of the MCU when a failure has been detected by a safety mechanism.
- 2) MCU_FAULT_FREE_STATE: the state of the MCU when no failure has been detected by a safety mechanism AND the MCU operates according to the functional specification AND according to the intended system integrator's software configuration
- IFX.Version: 3
- ReqIF-WF.Type: Information

#### SUGA-FJEE-DBJE-BBHA: Specific assumptions of use
To make use of this tlsr use case, the system integrator shall ensure that the following assumptions of use are fulfilled:
- IFX.Version: 4
- ReqIF-WF.Type: Information

##### sug1605542052281-001
In case the system integrator uses EMS or ESR or external request unit inputs as part of system integrator's safety mechanism, it is assumed that the system integrator tests the safety mechanism once per MPFDTI that is defined by the system integrator.
Example: in xEV inverter application, EMS pin can be triggered by power module (for example IGBT module) to notify the failure detection in power module hardware so that the EMS notification can generate an NMI to the CPU. It is system integrator's responsibility to test this system-level safety mechanism within his/her own MPFDTI.
- ReqIF-WF.Type: Requirement

##### sug1605542052281-002
It is assumed that the system integrator's software takes a decision upon SMU reaction (interrupt, NMI or reset).
For example, in case a MCU is reset by SMU reaction, system integrator's software is responsible to check the cause of the SMU reset reaction in order to evaluate if the MCU is in reliable status. (for example check if the fault was transient or is still existing)
- ReqIF-WF.Type: Requirement

#### AGRA-FJEE-DBCD-IABH: Application diagram
The application diagram for this tlsr use case is shown below.
Application diagram for the tlsr use case Internal failure reporting interface
- IFX.Version: 4
- ReqIF-WF.Type: Information

#### RJQA-FJEE-DBFD-DEAD: Internal and external safety mechanisms
For this use case, the following internal safety mechanisms are considered to be configured, activated and used in addition to those stated in Internal and external safety mechanisms. All external safety mechanisms mentioned below shall be provided by the system integrator.
- IFX.Version: 11
- ReqIF-WF.Type: Information

##### RJQA-FJEE-DBFD-DEAD-001
The system integrator shall ensure that the external safety mechanisms listed here are implemented and that the internal safety mechanisms listed here are configured and activated when using the TUC Internal failure reporting interface:
ESM[SW]:MCU:LBIST
ESM[SW]:SCU:CONFIG_READBACK
ESM[SW]:SMM:CONFIG_READBACK
ESM[SW]:SMU:CONFIG_READBACK
ESM[SW]:SMU:ALARM_SIGNAL_TEST
SM[HW]:FPI:TRANSACTION_INTEGRITY
SM[HW]:MCU:LBIST
SM[HW]:MCU:LBIST_COMPLETE
SM[HW]:SCU:REG_MONITOR
SM[HW]:SMM:REG_MONITOR
SM[HW]:SMU:ALIVE_MONITOR
SM[HW]:SMU:LOCK
SM[HW]:SMU:REG_MONITOR
SM[HW]:SMU:RT
- ReqIF-WF.Type: Requirement

### NURA-FJEJ-HHFC-FJGJ: External failure reporting interface
- Any failure detected by; 1) the hardware safety mechanism of the MCU or; 2) the software safety mechanism of the MCU or; 3) the system integrator's safety mechanism can be notified to the system integrator by the safety and security alarm management unit.
- External Failure Reporting Interface is an ability of the MCU Safe State Support architecture to enable hardware or software safety mechanisms to communicate with the system for the purpose of indicating the presence of a failure.
- The External Failure Reporting Interface indicates two states 1) MCU_FAULT_STATE: the state of the MCU when a failure has been detected by a safety mechanism. 2) MCU_FAULT_FREE_STATE: the state of the MCU when no failure has been detected by a safety mechanism AND the MCU operates according to the functional specification AND according to the intended system integrator's software configuration
- IFX.Version: 3
- ReqIF-WF.Type: Information

#### NHHA-FJEE-DBJE-HHHH: Specific assumptions of use
To make use of this tlsr use case, the system integrator shall ensure that the following assumptions of use are fulfilled:
- IFX.Version: 5
- ReqIF-WF.Type: Information

##### nhh1605542058888-001
In case the system integrator uses EMS or ESR or external request unit inputs as part of system integrator's safety mechanism, it is assumed that the system integrator test the safety mechanism once per MPFDTI that is defined by the system integrator.
Example: in xEV inverter application, EMS pin can be triggered by power module (for example IGBT module) to notify the failure detection in power module hardware so that the EMS notification can generate an NMI to the CPU. It is system integrator's responsibility to test this system-level safety mechanism within his/her own MPFDTI.
- ReqIF-WF.Type: Requirement

##### nhh1605542058888-002
In case the system integrator uses the EMS output as an error notification interface (instead of or together with FSP), it is assumed that the system integrator tests the EMS output activation once per MPFDTI that is defined by the system integrator.
- ReqIF-WF.Type: Requirement

#### UKPA-FJEE-DBCE-FAHI: Application diagram
The application diagram for this tlsr use case is shown below.
Application diagram for the tlsr use case External failure reporting interface
- IFX.Version: 4
- ReqIF-WF.Type: Information

#### QSEA-FJEE-DBFE-BBIC: Internal and external safety mechanisms
For this use case, the following Internal safety mechanisms are considered to be configured, activated and used in addition to those stated in Internal and external safety mechanisms. All external safety mechanisms mentioned below shall be provided by the system integrator.
- IFX.Version: 11
- ReqIF-WF.Type: Information

##### QSEA-FJEE-DBFE-BBIC-001
The system integrator shall ensure that the external safety mechanisms listed here are implemented and that the internal safety mechanisms listed here are configured and activated when using the TUC External failure reporting interface:
ESM[SW]:MCU:LBIST
ESM[SW]:SCU:CONFIG_READBACK
ESM[SW]:SMM:CONFIG_READBACK
ESM[SW]:SMU:ALARM_SIGNAL_TEST
ESM[SW]:SMU:CONFIG_READBACK
ESM[HW]:SYS:FSP_ERROR_PIN_MONITOR
SM[HW]:FPI:TRANSACTION_INTEGRITY
SM[HW]:MCU:LBIST
SM[HW]:MCU:LBIST_COMPLETE
SM[HW]:SCU:REG_MONITOR
SM[HW]:SMM:REG_MONITOR
SM[HW]:SMU:ALIVE_MONITOR
SM[HW]:SMU:CRITICAL_ALARM
SM[HW]:SMU:FSP_MONITOR
SM[HW]:SMU:LOCK
SM[HW]:SMU:REG_MONITOR
SM[HW]:SMU:RT
- ReqIF-WF.Type: Requirement

### CVRA-FJEJ-HHFD-FCAD: Alternate external failure reporting interface
- Any plausible common cause failure detection by the hardware safety mechanism of the MCU can be notified to the system by the SMU.
- Alternate External Failure Reporting Interface is an ability of the MCU Safe State Support architecture to enable hardware safety mechanisms to communicate with the system for the purpose of indicating the presence of a plausible common cause failure. (for example voltage, clock, temperature, etc.)
- The Alternate External Failure Reporting Interface indicates two states 1) MCU_FAULT_STATE: the state of the MCU when a failure has been detected by a safety mechanism. 2) MCU_FAULT_FREE_STATE: the state of the MCU when no failure has been detected by a safety mechanism AND the MCU operates according to the functional specification AND according to the intended system integrator's software configuration
- IFX.Version: 3
- ReqIF-WF.Type: Information

#### NMKA-FJEE-DBJF-EJBE: Specific assumptions of use
There are no specific assumptions of use for this use case.
- IFX.Version: 3
- ReqIF-WF.Type: Information

#### HPKA-FJEE-DBCF-CIIG: Application diagram
The application diagram for this tlsr use case is shown below.
Application diagram for the tlsr use case Alternate external failure reporting interface
- IFX.Version: 4
- ReqIF-WF.Type: Information

#### GMEA-FJEE-DBFE-IICJ: Internal and external safety mechanisms
For this use case, the following internal safety mechanisms are considered to be configured, activated and used in addition to those stated in Internal and external safety mechanisms. All external safety mechanisms mentioned below shall be provided by the system integrator.
- IFX.Version: 10
- ReqIF-WF.Type: Information

##### GMEA-FJEE-DBFE-IICJ-001
The system integrator shall ensure that the external safety mechanisms listed here are implemented and that the internal safety mechanisms listed here are configured and activated when using the TUC Alternate external failure reporting interface:
ESM[HW]:SYS:FSP_ERROR_PIN_MONITOR
ESM[SW]:MCU:LBIST
ESM[SW]:SMU:ALARM_SIGNAL_TEST
ESM[SW]:SMU:STDBY_MONBIST
ESM[SW]:SMU:CONFIG_READBACK
SM[HW]:FPI:TRANSACTION_INTEGRITY
SM[HW]:MCU:LBIST
SM[HW]:MCU:LBIST_COMPLETE
SM[HW]:SMU:CRITICAL_ALARM
SM[HW]:SMU:DIVERSE_REDUNDANCY
SM[HW]:SMU:FSP_MONITOR
SM[HW]:SMU:LOCK
SM[HW]:SMU:REG_MONITOR
SM[HW]:SMU:RT
- ReqIF-WF.Type: Requirement

### RRTA-FJEJ-HHCH-GEJI: Common cause failure by power
Independence from Power Management System (PMS) failure is realized by meeting requirements from the TUC Power management, mainly by:
- Internal safety mechanisms of PMS: PMS is the only FB that receives external power source, generates internal voltage supplies and distributes generated supply voltages to the whole MCU.
- External safety mechanism (for example external monitoring device) : safety mechanisms to monitor the safety-related failure modes of the PMS is reliable only up to specified maximum admitted voltage.
Refer to Power management for more details.
- IFX.Version: 4
- ReqIF-WF.Type: Information

#### KRVA-FJEE-CHGD-BHBH: Specific assumptions of use
There are no specific assumptions of use for this use case.
- IFX.Version: 3
- ReqIF-WF.Type: Information

#### IAHA-FJEE-DBBE-HIFC: Application diagram
Not applicable for this TUC.
- IFX.Version: 3
- ReqIF-WF.Type: Information

#### AVAA-FJEE-DBEC-JEII: Internal and external safety mechanisms
Independence from Power Management System (PMS) failure is realized by meeting requirements from Power management.
- IFX.Version: 5
- ReqIF-WF.Type: Information

### ZTEA-FJEJ-HHCI-FBCD: Common cause failure by clock
Independence from failure in the clocking system is realized by meeting requirements from the TUC Clock management, mainly by:
- Internal safety mechanisms of CLOCK : CLOCK generates the internal primary clock source by receiving external clock source and distributes generated clocks for all MCU functions.
Note: External monitoring device is not needed as AURIX™ TC43x has an independent clock (back-up clock) to detect any failure of main clocks.
Refer to Clock management for more details.
- IFX.Version: 4
- ReqIF-WF.Type: Information

#### GBUA-FJEE-CHGD-HIGE: Specific assumptions of use
There are no specific assumptions of use for this use case.
- IFX.Version: 3
- ReqIF-WF.Type: Information

#### BFWA-FJEE-DBBF-FJFG: Application diagram
Not applicable for this TUC.
- IFX.Version: 3
- ReqIF-WF.Type: Information

#### GIVA-FJEE-DBEC-GGGH: Internal and external safety mechanisms
Independence from failure in the clocking system is realized by meeting requirements from the TUC Clock management.
- IFX.Version: 5
- ReqIF-WF.Type: Information

### JEOA-FJEJ-HHEJ-EFCC: Common cause failure by over-temperature
Since the over-temperature which is out of the range specified by the MCU specification in the data sheet would cause the unreliable MCU behavior, it must be monitored or detected.
- IFX.Version: 4
- ReqIF-WF.Type: Information

#### SOUA-FJEE-DAII-AHDG: Specific Assumptions of Use
There are no specific assumptions of use for this use case.
- IFX.Version: 2
- ReqIF-WF.Type: Information

#### XWXA-FJEE-DBBH-CDAB: Application diagram
The application diagram for this tlsr use case is shown below.
Application diagram for the tlsr use case Common cause failure by over-temperature
- IFX.Version: 3
- ReqIF-WF.Type: Information

#### IKDA-FJEE-DBEE-CACG: Internal and external safety mechanisms
For this use case, the following internal safety mechanisms are considered to be configured, activated and used in addition to those stated in Internal and external safety mechanisms. All external safety mechanisms mentioned below shall be provided by the system integrator.
- IFX.Version: 6
- ReqIF-WF.Type: Information

##### IKDA-FJEE-DBEE-CACG-001
The system integrator shall implement the safety mechanisms listed here when using the TUC Common cause failure by over-temperature:
ESM[SW]:VTMON:DTS_RESULT
SM[HW]:FPI:TRANSACTION_INTEGRITY
SM[HW]:VTMON:REG_MONITOR
SM[HW]:VTMON:TEMPERATURE_MONITOR
- ReqIF-WF.Type: Requirement

### GNFA-FJEJ-HHEA-EFHJ: Common cause failure by system management
Independence from failure in the system management is realized by meeting requirements below.
- Safety mechanisms for system mode management: the SMM coordinates the system mode transition between Reset, Stand-by, Run and Sleep. This is addressed in the TUC System mode management.
- Product configuration by system control unit: the Product Configuration function of the SCU allows for each microcontroller product to have a different set of configurations. Wrong product configuration is monitored by homogeneous redundancy (for example safety flip-flops).
- IFX.Version: 4
- ReqIF-WF.Type: Information

#### OZTA-FJEE-DBJJ-CJGE: Specific assumptions of use
There are no specific assumptions of use for this use case.
- IFX.Version: 3
- ReqIF-WF.Type: Information

#### BJNA-FJEE-DBBI-DADJ: Application diagram
Not applicable for this TUC.
- IFX.Version: 3
- ReqIF-WF.Type: Information

#### HTEA-FJEE-DBEH-JCAJ: Internal and external safety mechanisms
For this use case, the following internal safety mechanisms are considered to be configured, activated and used in addition to those stated in Internal and external safety mechanisms. All external safety mechanisms mentioned below shall be provided by the system integrator.
- IFX.Version: 9
- ReqIF-WF.Type: Information

##### HTEA-FJEE-DBEH-JCAJ-001
The system integrator shall implement the safety mechanisms listed here when using the TUC Common cause failure by system management:
ESM[SW]:SCU:CONFIG_READBACK
ESM[SW]:SMU:ALARM_SIGNAL_TEST
SM[HW]:FPI:TRANSACTION_INTEGRITY
SM[HW]:SCU:REG_MONITOR
- ReqIF-WF.Type: Requirement

### XVRA-FJEJ-HHEB-FGHC: Common cause failure by Test and Debug functions
This tlsr use case considers the scenario in which common cause failures can occur due to faults in the Test and Debug functions. The following 3 situations are being considered in this TUC:
1. An unintended activation of the DEBUG function. For example an unintentional activation of Set Breakpoint function.
2. An unintended activation of the TEST function. For example an unintentional activation of Device test and analysis function or Design FullScan function.
3. An unintended activation of the VMTEST function. For example an unintentional activation of Memory test function.
- IFX.Version: 4
- ReqIF-WF.Type: Information

#### ZQFA-FJEE-DBJA-JFFF: Specific assumptions of use
There are no specific assumptions of use for this use case.
- IFX.Version: 3
- ReqIF-WF.Type: Information

#### SGXA-FJEE-DBCJ-DEIG: Application diagram
The application diagram for this tlsr use case is shown below.
Application diagram for the tlsr use case Common cause failure by Test and Debug functions
- IFX.Version: 4
- ReqIF-WF.Type: Information

#### ALMA-FJEE-DBEH-ICAJ: Internal and external safety mechanisms
For this use case, the following internal safety mechanisms are considered to be configured, activated and used in addition to those stated in Internal and external safety mechanisms. All external safety mechanisms mentioned below shall be provided by the system integrator.
- IFX.Version: 7
- ReqIF-WF.Type: Information

##### ALMA-FJEE-DBEH-ICAJ-001
The system integrator shall implement the safety mechanisms listed here when using the TUC Common cause failure by Test and Debug functions:
ESM[SW]:SMU:ALARM_SIGNAL_TEST
ESM[SW]:VMT:ISR_MONITOR
SM[HW]:DEBUG:FFI_CONTROL
SM[HW]:DFT:FFI_CONTROL
- ReqIF-WF.Type: Requirement

### MWNA-FJEJ-HHED-EIIB: Common cause failure by common external resources
The following external resources are plausible common cause failures to the MCU:
- External power supply
- External clock source
- External reset system
- IFX.Version: 4
- ReqIF-WF.Type: Information

#### WWXA-FJEE-DBJB-EFEB: Specific assumptions of use
To make use of this tlsr use case, the system integrator shall ensure that the following assumptions of use are fulfilled:
- IFX.Version: 4
- ReqIF-WF.Type: Information

##### wwx1605542025652-001
It is assumed that the system integrator detects over-voltage conditions on the external power supply and immediately disable the external power supply to the MCU.
Rationale: a supply voltage deviation above the specified maximum admitted range can lead to permanent failures and physical damage to the MCU.
- ReqIF-WF.Type: Requirement

##### wwx1605542025652-002
It is assumed that the system integrator monitors the unintentional reset request to the MCU from system integrator's reset circuit.
Note: upon detection of such failure, it is assumed that the system integrator transit the system into safe state.
- ReqIF-WF.Type: Requirement

##### wwx1605542025652-003
It is assumed that the system integrator detects the brain-dead MCU status where MCU is not alive after PORST release.
- ReqIF-WF.Type: Requirement

#### BNGA-FJEE-DBCA-IEGB: Application diagram
The application diagram for this tlsr use case is shown below.
Application diagram for the tlsr use case Common cause failure by common external resources
- IFX.Version: 4
- ReqIF-WF.Type: Information

#### JJTA-FJEE-DBFA-BJDF: Internal and external safety mechanisms
The safety of the external power supply, external clock source and external reset system are considered in each infrastructure TUC of the MCU.
To ensure avoidance of Common cause failure by common external resources, the system integrator shall implement the following TUCs:
1. Power management for the monitoring of external power supply failure
2. Clock management for the monitoring of external clock source failure
3. System mode management for the monitoring of external reset system failure
- IFX.Version: 5
- ReqIF-WF.Type: Information

### HHYA-FJEJ-HHEI-EFFG: Monitoring of slave access by unintended masters
This tlsr use case was developed to prevent interference from microcontroller unit masters unintentionally accessing slave functional blocks involved in a safety related application.
Due to a systematic fault in the application software, a master microcontroller unit resource (for example Central processing unit, direct memory access) could try to access a slave functional block (for example analog to digital converter, asynchronous synchronous interface) involved in a safety related application.
Note: Unintentional master functional block's access might not lead to direct violation of a TLSR but is a plausible interference to the TLSR use case (TUC).
As shown in the Application diagram, master and slave functional blocks are connected through different bus systems such as flexible peripheral interconnect, low latency interconnect and shared resource interconnect.
Each slave functional block has a dedicated slave interface that connects it to the corresponding bus and handles access requests from the bus to the peripheral. This slave interface features access protection mechanisms to restrict the access to the peripheral, as explained in the chapter "System Interconnect" of the AURIX™ TC43x User's Manual.
This tlsr use case shows which safety mechanisms shall be configured/enabled by the system integrator to ensure freedom from interference between hardware elements.
- IFX.Version: 5
- ReqIF-WF.Type: Information

#### MMQA-FJEE-DBJC-HFHB: Specific assumptions of use
To make use of this tlsr use case, the system integrator shall ensure that the following assumptions of use are fulfilled:
- IFX.Version: 7
- ReqIF-WF.Type: Information

##### mmq1605542038682-001
The system integrator is assumed to mitigate systematic failures in application software.
Alarms or Interrupts from Safety Mechanisms which control software failures (for example access protection, MPU, etc.) shall not be ignored, but treated according to application needs. A reasonable alarm or interrupt reaction could be application reset to control the software causing the violation. One violation per driving cycle caused by soft errors or unintended access protection violations (hence systematic failure in application software) shall be assumed as normal behavior.
- ReqIF-WF.Type: Requirement

#### PWPA-FJEE-DBCC-CIBF: Application diagram
The application diagram for this tlsr use case is shown below.
Application diagram for the tlsr use case Monitoring of slave access by unintended masters
- IFX.Version: 4
- ReqIF-WF.Type: Information

#### FVLA-FJEE-DBFB-IIBJ: Internal and external safety mechanisms
For this use case, the following internal safety mechanisms are considered to be configured, activated and used in addition to those stated in Internal and external safety mechanisms. All external safety mechanisms mentioned below shall be provided by the system integrator.
- IFX.Version: 13
- ReqIF-WF.Type: Information

##### FVLA-FJEE-DBFB-IIBJ-001
The system integrator shall ensure that the internal safety mechanisms listed here are configured and activated when using the TUC Monitoring of slave access by unintended masters:
Note: access protection can be selectively applied to those functional blocks being used by a safety related function. For this purpose, the system integrator can select only the safety mechanisms from this list that are found to be applicable.
SM[HW]:ADC:CFG_AS_AP
SM[HW]:ADC:ENDINIT
SM[HW]:ADC:SAFETY_ENDINIT
SM[HW]:ADC:SV_AP
SM[HW]:ASCLIN:CFG_AS_AP
SM[HW]:ASCLIN:ENDINIT
SM[HW]:ASCLIN:SAFETY_ENDINIT
SM[HW]:ASCLIN:SV_AP
SM[HW]:CAN:CFG_AS_AP
SM[HW]:CAN:ENDINIT
SM[HW]:CAN:SAFETY_ENDINIT
SM[HW]:CAN:SV_AP
SM[HW]:CANXL:ENDINIT
SM[HW]:CANXL:SAFETY_ENDINIT
SM[HW]:CANXL:CFG_AS_AP
SM[HW]:CANXL:SV_AP
SM[HW]:CLOCK:CFG_AS_AP
SM[HW]:CLOCK:ENDINIT
SM[HW]:CLOCK:SAFETY_ENDINIT
SM[HW]:CLOCK:SV_AP
SM[HW]:CPU:STARTUP_PROTECTION
SM[HW]:CPU:CFG_AS_AP
SM[HW]:CPU:ENDINIT
SM[HW]:CPU:SAFETY_ENDINIT
SM[HW]:CPU:SV_AP
SM[HW]:CSRM:CFG_AS_AP
SM[HW]:CSS:SV_AP
SM[HW]:CSS:CFG_AS_AP
SM[HW]:CSS:SAFETY_ENDINIT
SM[HW]:DEBUG:CFG_AS_AP
SM[HW]:DFT:CFG_AS_AP
SM[HW]:DFT:ENDINIT
SM[HW]:DFT:SAFETY_ENDINIT
SM[HW]:DFT:SV_AP
SM[HW]:DMA:CFG_AS_AP
SM[HW]:DMA:SAFETY_ENDINIT
SM[HW]:DMA:SV_AP
SM[HW]:DRE:CFG_AS_AP
SM[HW]:DRE:ENDINIT
SM[HW]:DRE:SAFETY_ENDINIT
SM[HW]:DRE:SV_AP
SM[HW]:EGTM:CFG_AS_AP
SM[HW]:EGTM:ENDINIT
SM[HW]:EGTM:SAFETY_ENDINIT
SM[HW]:EGTM:SV_AP
SM[HW]:ERAY:CFG_AS_AP
SM[HW]:ERAY:ENDINIT
SM[HW]:ERAY:SAFETY_ENDINIT
SM[HW]:ERAY:SV_AP
SM[HW]:FCE:CFG_AS_AP
SM[HW]:FPI:ADDRESS_MAP_MONITORING
SM[HW]:FPI:CFG_AS_AP
SM[HW]:FPI:ENDINIT
SM[HW]:FPI:SAFETY_ENDINIT
SM[HW]:FPI:SV_AP
SM[HW]:GETH:CFG_AS_AP
SM[HW]:GETH:ENDINIT
SM[HW]:GETH:SAFETY_ENDINIT
SM[HW]:GETH:SV_AP
SM[HW]:GPT12:CFG_AS_AP
SM[HW]:GPT12:ENDINIT
SM[HW]:GPT12:SAFETY_ENDINIT
SM[HW]:GPT12:SV_AP
SM[HW]:GST:CFG_AS_AP
SM[HW]:GST:ENDINIT
SM[HW]:GST:SAFETY_ENDINIT
SM[HW]:GST:SV_AP
SM[HW]:GTM:CFG_AS_AP
SM[HW]:GTM:ENDINIT
SM[HW]:GTM:SAFETY_ENDINIT
SM[HW]:GTM:SV_AP
SM[HW]:HSPHY:CFG_AS_AP
SM[HW]:HSPHY:ENDINIT
SM[HW]:HSPHY:SAFETY_ENDINIT
SM[HW]:HSPHY:SV_AP
SM[HW]:HSSL:CFG_AS_AP
SM[HW]:HSSL:ENDINIT
SM[HW]:HSSL:SAFETY_ENDINIT
SM[HW]:HSSL:SV_AP
SM[HW]:I2C:CFG_AS_AP
SM[HW]:I2C:ENDINIT
SM[HW]:I2C:SAFETY_ENDINIT
SM[HW]:I2C:SV_AP
SM[HW]:IR:CFG_AS_AP
SM[HW]:IR:SV_AP
SM[HW]:IR:SAFETY_ENDINIT
SM[HW]:LETH:CFG_AS_AP
SM[HW]:LETH:ENDINIT
SM[HW]:LETH:SAFETY_ENDINIT
SM[HW]:LETH:SV_AP
SM[HW]:LLI:ADDRESS_MAP_MONITORING
SM[HW]:LLI:CFG_AS_AP
SM[HW]:LLI:SV_AP
SM[HW]:LMU:CFG_AS_AP
SM[HW]:LMU:SAFETY_ENDINIT
SM[HW]:LMU:SV_AP
SM[HW]:MSC:CFG_AS_AP
SM[HW]:NVM:SAFETY_ENDINIT
SM[HW]:NVM:CFG_AS_AP
SM[HW]:NVM:STARTUP_PROTECTION
SM[HW]:NVM:SV_AP
SM[HW]:NVMR:CFG_AS_AP
SM[HW]:NVMR:SAFETY_ENDINIT
SM[HW]:NVMR:SV_AP
SM[HW]:PCIE:CFG_AS_AP
SM[HW]:PCIE:ENDINIT
SM[HW]:PCIE:SAFETY_ENDINIT
SM[HW]:PCIE:SV_AP
SM[HW]:PMS:CFG_AS_AP
SM[HW]:PMS:ENDINIT
SM[HW]:PMS:SAFETY_ENDINIT
SM[HW]:PMS:SV_AP
SM[HW]:PORTS:CFG_AS_AP
SM[HW]:PORTS:ENDINIT
SM[HW]:PORTS:SAFETY_ENDINIT
ESM[SW]:PPU:BUS_ERROR_HANDLING
SM[HW]:PORTS:SV_AP
SM[HW]:PPU:CFG_AS_AP
SM[HW]:PPU:ENDINIT
SM[HW]:PPU:SAFETY_ENDINIT
SM[HW]:PPU:SV_AP
SM[HW]:PSI5:CFG_AS_AP
SM[HW]:PSI5:ENDINIT
SM[HW]:PSI5:SAFETY_ENDINIT
SM[HW]:PSI5:SV_AP
SM[HW]:PSI5S:CFG_AS_AP
SM[HW]:PSI5S:ENDINIT
SM[HW]:PSI5S:SAFETY_ENDINIT
SM[HW]:PSI5S:SV_AP
SM[HW]:QSPI:CFG_AS_AP
SM[HW]:QSPI:ENDINIT
SM[HW]:QSPI:SAFETY_ENDINIT
SM[HW]:QSPI:SV_AP
SM[HW]:RDMA:CFG_AS_AP
SM[HW]:RDMA:ENDINIT
SM[HW]:RDMA:SAFETY_ENDINIT
SM[HW]:RDMA:SV_AP
SM[HW]:RIF:CFG_AS_AP
SM[HW]:RIF:ENDINIT
SM[HW]:RIF:SAFETY_ENDINIT
SM[HW]:RIF:SV_AP
SM[HW]:RMEM:CFG_AS_AP
SM[HW]:RMEM:SAFETY_ENDINIT
SM[HW]:RMEM:SV_AP
SM[HW]:SCU:CFG_AS_AP
SM[HW]:SCU:ENDINIT
SM[HW]:SCU:SAFETY_ENDINIT
SM[HW]:SCU:SV_AP
SM[HW]:SDMMC:CFG_AS_AP
SM[HW]:SDMMC:ENDINIT
SM[HW]:SDMMC:SAFETY_ENDINIT
SM[HW]:SDMMC:SV_AP
SM[HW]:SENT:CFG_AS_AP
SM[HW]:SENT:ENDINIT
SM[HW]:SENT:SAFETY_ENDINIT
SM[HW]:SENT:SV_AP
SM[HW]:SMM:CFG_AS_AP
SM[HW]:SMM:ENDINIT
SM[HW]:SMM:SAFETY_ENDINIT
SM[HW]:SMM:STARTUP_PROTECTION
SM[HW]:SMM:SV_AP
SM[HW]:SMU:CFG_AS_AP
SM[HW]:SMU:LOCK
SM[HW]:SMU:ENDINIT
SM[HW]:SMU:SAFETY_ENDINIT
SM[HW]:SMU:SV_AP
SM[HW]:SPU:CFG_AS_AP
SM[HW]:SPU:ENDINIT
SM[HW]:SPU:SAFETY_ENDINIT
SM[HW]:SPU:SV_AP
SM[HW]:SRI:SRI_ADDRESS_MAP_MONITORING
SM[HW]:SRI:CFG_AS_AP
SM[HW]:SRI:SAFETY_ENDINIT
SM[HW]:SRI:SV_AP
SM[HW]:TRACE:CFG_AS_AP
SM[HW]:VMT:CFG_AS_AP
SM[HW]:VMT:ENDINIT
SM[HW]:VMT:SAFETY_ENDINIT
SM[HW]:VMT:SV_AP
SM[HW]:VTMON:CFG_AS_AP
SM[HW]:VTMON:ENDINIT
SM[HW]:VTMON:SAFETY_ENDINIT
SM[HW]:VTMON:SV_AP
SM[HW]:WTU:CFG_AS_AP
SM[HW]:WTU:SAFETY_ENDINIT
SM[HW]:WTU:SV_AP
SM[HW]:XSPI:CFG_AS_AP
SM[HW]:XSPI:ENDINIT
SM[HW]:XSPI:SAFETY_ENDINIT
SM[HW]:XSPI:SV_AP
These safety mechanisms are targeting systematic faults in the software, therefore they will not appear in FMEDA.
Some of the functional blocks listed here might not be available in a particular AURIX™ TC4xx device. Please refer to the "Device feature set" chapter in the Datasheet for more details.
- ReqIF-WF.Type: Requirement

### VAXA-FJGF-ACEC-EBHE: Monitoring of interference from software elements
If in a multi-core context multiple software elements with different ASIL ratings coexist, a freedom from interference analysis must be carried out. During this analysis, the following potential failure modes of software elements shall be considered.
Timing and execution
With respect to timing constraints, the effects of faults such as those listed below can be considered for the software elements executed in each software partition:
- blocking of execution
- deadlocks
- livelocks
- incorrect allocation of execution time; OR
- incorrect synchronization between software elements
Memory
With respect to memory, the effects of faults such as those listed below can be considered for software elements executed in each software partition:
- corruption of content
- inconsistent data (for example due to update during data fetch)
- stack overflow or underflow; OR
- read or write access to memory allocated to another software element
Exchange of information
With respect to the exchange of information, the causes for faults or effects of faults such as those listed below can be considered for each sender or each receiver:
- repetition of information
- loss of information
- delay of information
- insertion of information
- masquerade or incorrect addressing of information
- incorrect sequence of information
- corruption of information
- asymmetric information sent from a sender to multiple receivers
- information from a sender received by only a subset of the receivers; OR
- blocking access to a communication channel
- IFX.Version: 5
- ReqIF-WF.Type: Information

#### IBAA-FJGF-ACEH-DEIA: Specific assumptions of use
There are no specific assumptions of use for this use case.
- IFX.Version: 3
- ReqIF-WF.Type: Information

#### WUYA-FJGF-ACFD-JBAJ: Application diagram
Not applicable for this TUC.
- IFX.Version: 3
- ReqIF-WF.Type: Information

#### OVUA-FJGF-ACFF-JGGE: Internal and external safety mechanisms
For this use case, the following internal safety mechanisms are considered to be configured, activated and used in addition to those stated in Internal and external safety mechanisms. All external safety mechanisms mentioned below shall be provided by the system integrator.
- IFX.Version: 10
- ReqIF-WF.Type: Information

##### ovu1607613660775-001
The system integrator shall ensure that the external safety mechanisms listed here are implemented and that the internal safety mechanisms listed here are configured and activated when using the TUC Monitoring of interference from software elements:
ESM[SW]:MCU:LBIST
SM[HW]:CPU:CODE_MPU
SM[HW]:MCU:LBIST
SM[HW]:MCU:LBIST_COMPLETE
SM[HW]:CPU:DATA_MPU
- ReqIF-WF.Type: Requirement

##### OVUA-FJGF-ACFF-JGGE-002
The system integrator shall ensure that the internal safety mechanisms listed here are configured and activated when using the TUC Monitoring of interference from software elements:
Note: access protection can be selectively applied to those functional blocks being used by a safety related function. For this purpose, the system integrator can select only the safety mechanisms from this list that are found to be applicable.
SM[HW]:ADC:CFG_AS_AP
SM[HW]:ADC:ENDINIT
SM[HW]:ADC:SAFETY_ENDINIT
SM[HW]:ADC:SV_AP
SM[HW]:ASCLIN:CFG_AS_AP
SM[HW]:ASCLIN:ENDINIT
SM[HW]:ASCLIN:SAFETY_ENDINIT
SM[HW]:ASCLIN:SV_AP
SM[HW]:CAN:CFG_AS_AP
SM[HW]:CAN:ENDINIT
SM[HW]:CAN:SAFETY_ENDINIT
SM[HW]:CAN:SV_AP
SM[HW]:CANXL:ENDINIT
SM[HW]:CANXL:SAFETY_ENDINIT
SM[HW]:CANXL:CFG_AS_AP
SM[HW]:CANXL:SV_AP
SM[HW]:CLOCK:CFG_AS_AP
SM[HW]:CLOCK:ENDINIT
SM[HW]:CLOCK:SAFETY_ENDINIT
SM[HW]:CLOCK:SV_AP
SM[HW]:CPU:STARTUP_PROTECTION
SM[HW]:CPU:CFG_AS_AP
SM[HW]:CPU:ENDINIT
SM[HW]:CPU:SAFETY_ENDINIT
SM[HW]:CPU:SV_AP
SM[HW]:CSRM:CFG_AS_AP
SM[HW]:CSS:SV_AP
SM[HW]:CSS:CFG_AS_AP
SM[HW]:CSS:SAFETY_ENDINIT
SM[HW]:DEBUG:CFG_AS_AP
SM[HW]:DFT:CFG_AS_AP
SM[HW]:DFT:ENDINIT
SM[HW]:DFT:SAFETY_ENDINIT
SM[HW]:DFT:SV_AP
SM[HW]:DMA:CFG_AS_AP
SM[HW]:DMA:SAFETY_ENDINIT
SM[HW]:DMA:SV_AP
SM[HW]:DRE:CFG_AS_AP
SM[HW]:DRE:ENDINIT
SM[HW]:DRE:SAFETY_ENDINIT
SM[HW]:DRE:SV_AP
SM[HW]:EGTM:CFG_AS_AP
SM[HW]:EGTM:ENDINIT
SM[HW]:EGTM:SAFETY_ENDINIT
SM[HW]:EGTM:SV_AP
SM[HW]:ERAY:CFG_AS_AP
SM[HW]:ERAY:ENDINIT
SM[HW]:ERAY:SAFETY_ENDINIT
SM[HW]:ERAY:SV_AP
SM[HW]:FCE:CFG_AS_AP
SM[HW]:FPI:ADDRESS_MAP_MONITORING
SM[HW]:FPI:CFG_AS_AP
SM[HW]:FPI:ENDINIT
SM[HW]:FPI:SAFETY_ENDINIT
SM[HW]:FPI:SV_AP
SM[HW]:GETH:CFG_AS_AP
SM[HW]:GETH:ENDINIT
SM[HW]:GETH:SAFETY_ENDINIT
SM[HW]:GETH:SV_AP
SM[HW]:GPT12:CFG_AS_AP
SM[HW]:GPT12:ENDINIT
SM[HW]:GPT12:SAFETY_ENDINIT
SM[HW]:GPT12:SV_AP
SM[HW]:GST:CFG_AS_AP
SM[HW]:GST:ENDINIT
SM[HW]:GST:SAFETY_ENDINIT
SM[HW]:GST:SV_AP
SM[HW]:GTM:CFG_AS_AP
SM[HW]:GTM:ENDINIT
SM[HW]:GTM:SAFETY_ENDINIT
SM[HW]:GTM:SV_AP
SM[HW]:HSPHY:CFG_AS_AP
SM[HW]:HSPHY:ENDINIT
SM[HW]:HSPHY:SAFETY_ENDINIT
SM[HW]:HSPHY:SV_AP
SM[HW]:HSSL:CFG_AS_AP
SM[HW]:HSSL:ENDINIT
SM[HW]:HSSL:SAFETY_ENDINIT
SM[HW]:HSSL:SV_AP
SM[HW]:I2C:CFG_AS_AP
SM[HW]:I2C:ENDINIT
SM[HW]:I2C:SAFETY_ENDINIT
SM[HW]:I2C:SV_AP
SM[HW]:IR:CFG_AS_AP
SM[HW]:IR:SV_AP
SM[HW]:IR:SAFETY_ENDINIT
SM[HW]:LETH:CFG_AS_AP
SM[HW]:LETH:ENDINIT
SM[HW]:LETH:SAFETY_ENDINIT
SM[HW]:LETH:SV_AP
SM[HW]:LLI:ADDRESS_MAP_MONITORING
SM[HW]:LLI:CFG_AS_AP
SM[HW]:LLI:SV_AP
SM[HW]:LMU:CFG_AS_AP
SM[HW]:LMU:SAFETY_ENDINIT
SM[HW]:LMU:SV_AP
SM[HW]:MSC:CFG_AS_AP
SM[HW]:NVM:SAFETY_ENDINIT
SM[HW]:NVM:CFG_AS_AP
SM[HW]:NVM:STARTUP_PROTECTION
SM[HW]:NVM:SV_AP
SM[HW]:NVMR:CFG_AS_AP
SM[HW]:NVMR:SAFETY_ENDINIT
SM[HW]:NVMR:SV_AP
SM[HW]:PCIE:CFG_AS_AP
SM[HW]:PCIE:ENDINIT
SM[HW]:PCIE:SAFETY_ENDINIT
SM[HW]:PCIE:SV_AP
SM[HW]:PMS:CFG_AS_AP
SM[HW]:PMS:ENDINIT
SM[HW]:PMS:SAFETY_ENDINIT
SM[HW]:PMS:SV_AP
SM[HW]:PORTS:CFG_AS_AP
SM[HW]:PORTS:ENDINIT
SM[HW]:PORTS:SAFETY_ENDINIT
ESM[SW]:PPU:BUS_ERROR_HANDLING
SM[HW]:PORTS:SV_AP
SM[HW]:PPU:CFG_AS_AP
SM[HW]:PPU:ENDINIT
SM[HW]:PPU:SAFETY_ENDINIT
SM[HW]:PPU:SV_AP
SM[HW]:PSI5:CFG_AS_AP
SM[HW]:PSI5:ENDINIT
SM[HW]:PSI5:SAFETY_ENDINIT
SM[HW]:PSI5:SV_AP
SM[HW]:PSI5S:CFG_AS_AP
SM[HW]:PSI5S:ENDINIT
SM[HW]:PSI5S:SAFETY_ENDINIT
SM[HW]:PSI5S:SV_AP
SM[HW]:QSPI:CFG_AS_AP
SM[HW]:QSPI:ENDINIT
SM[HW]:QSPI:SAFETY_ENDINIT
SM[HW]:QSPI:SV_AP
SM[HW]:RDMA:CFG_AS_AP
SM[HW]:RDMA:ENDINIT
SM[HW]:RDMA:SAFETY_ENDINIT
SM[HW]:RDMA:SV_AP
SM[HW]:RIF:CFG_AS_AP
SM[HW]:RIF:ENDINIT
SM[HW]:RIF:SAFETY_ENDINIT
SM[HW]:RIF:SV_AP
SM[HW]:RMEM:CFG_AS_AP
SM[HW]:RMEM:SAFETY_ENDINIT
SM[HW]:RMEM:SV_AP
SM[HW]:SCU:CFG_AS_AP
SM[HW]:SCU:ENDINIT
SM[HW]:SCU:SAFETY_ENDINIT
SM[HW]:SCU:SV_AP
SM[HW]:SDMMC:CFG_AS_AP
SM[HW]:SDMMC:ENDINIT
SM[HW]:SDMMC:SAFETY_ENDINIT
SM[HW]:SDMMC:SV_AP
SM[HW]:SENT:CFG_AS_AP
SM[HW]:SENT:ENDINIT
SM[HW]:SENT:SAFETY_ENDINIT
SM[HW]:SENT:SV_AP
SM[HW]:SMM:CFG_AS_AP
SM[HW]:SMM:ENDINIT
SM[HW]:SMM:SAFETY_ENDINIT
SM[HW]:SMM:STARTUP_PROTECTION
SM[HW]:SMM:SV_AP
SM[HW]:SMU:CFG_AS_AP
SM[HW]:SMU:LOCK
SM[HW]:SMU:ENDINIT
SM[HW]:SMU:SAFETY_ENDINIT
SM[HW]:SMU:SV_AP
SM[HW]:SPU:CFG_AS_AP
SM[HW]:SPU:ENDINIT
SM[HW]:SPU:SAFETY_ENDINIT
SM[HW]:SPU:SV_AP
SM[HW]:SRI:SRI_ADDRESS_MAP_MONITORING
SM[HW]:SRI:CFG_AS_AP
SM[HW]:SRI:SAFETY_ENDINIT
SM[HW]:SRI:SV_AP
SM[HW]:TRACE:CFG_AS_AP
SM[HW]:VMT:CFG_AS_AP
SM[HW]:VMT:ENDINIT
SM[HW]:VMT:SAFETY_ENDINIT
SM[HW]:VMT:SV_AP
SM[HW]:VTMON:CFG_AS_AP
SM[HW]:VTMON:ENDINIT
SM[HW]:VTMON:SAFETY_ENDINIT
SM[HW]:VTMON:SV_AP
SM[HW]:WTU:CFG_AS_AP
SM[HW]:WTU:SAFETY_ENDINIT
SM[HW]:WTU:SV_AP
SM[HW]:XSPI:CFG_AS_AP
SM[HW]:XSPI:ENDINIT
SM[HW]:XSPI:SAFETY_ENDINIT
SM[HW]:XSPI:SV_AP
These safety mechanisms are targeting systematic faults in the software, therefore they will not appear in FMEDA.
Some of the functional blocks listed here might not be available in a particular AURIX™ TC4xx device. Please refer to the "Device feature set" chapter in the Datasheet for more details.
- ReqIF-WF.Type: Requirement

## ZFQA-FJGA-GFAF-CJGC: External connection and system failures
Not applicable for AURIX™ TC43x.
- IFX.Version: 3
- ReqIF-WF.Type: Information

## XPVA-EIAF-IFJH-EGEF: Appendix
- IFX.Version: 2
- ReqIF-WF.Type: Information

### CSKA-FJAI-HEAI-BEBI: Code and implementation examples for ESMs
- IFX.Version: 2
- ReqIF-WF.Type: Information

#### PLGA-FDFB-IBFB-JGII: Code examples for PPU
The code examples provided here are not used in the FMEDA and are shown in the safety manual as 'information only'.
Pass and fail routines
Information only, provided as standard jump code segments used in all examples shown below.
passed:
		mov r26, PASS_CODE ; initial value, will change if test passes
		nop
		nop
		nop
		flag 1
		nop
		nop
		nop

failed:
		mov r26, FAIL_CODE ; initial value, will change if test passes
		nop
		nop
		flag 1
		nop
		nop
		nop

		;; EOF
		nop
		nop
		nop
		nop
Fault injection example for SM[HW]:PPU:VDSP_ERROR_CORRECTION
Injection of a double bit error:
SFTY_PASSWD 		 equ A90
SFTY_DIAG 		   equ A92
VEC_ECC_CTRL 		equ 549
SFTY_ERROR_STATUS 	equ A94

//Set the password by setting SFTY_PASSWD.PWD[1:0] to 10
                                    B
mov r1, 0x2
sr r1, [SFTY_PASSWD]
//
//Enable diag mode and SRAM error injection. For Memory Error Injection, set SFTY_DIAG.MEI[5:4] bits to 10
                                    B and to enable diagnostic mode set SFTY_DIAG.DI[31:30] to 10
                                    B
mov r1, 0x9555_5565
sr r1, [SFTY_DIAG]
//
// Turn off ECC protection and disable exceptions on VEC MEM by setting VEC_ECC_CTRL.DP[0] bit to 1
                                    B and VEC_ECC_CTRL.DE[1] bit to 1
                                    B
mov r1, 0x3
sr r1, [VEC_ECC_CTRL]
// Get data from VEC MEM
mov r2, 0x90000000
ldb r1, [r2]
mov r4, r1
// Flip two bits in the read data and store it back
bxor r1, r1, 1
mov r3, r1
bxor r3, r3, 2
stb r3, [r2]
sync
// Turn on ECC by setting VEC_ECC_CTRL.DP[0] to 0
                                    B
mov r1, 0x2
sr r1, [VEC_ECC_CTRL]
nop
nop
nop
nop
// Read the corrupted data
ld r1, [r2]
sync
nop
nop
nop
//
// Data should not be same as original data
cmp r4, r1
jz failed
//
// Check if SFTY_ERROR_STATUS.CPU[0] bit asserted
mov r5, 0x1
lr r6, [SFTY_ERROR_STATUS]
cmp r5, r6
jz passed
jnz failed
//
//Set the password by setting SFTY_PASSWD.PWD[1:0] to 10
                                    B
mov r0, 0x2
sr r0, [SFTY_PASSWD]
//
//Disable Diagnostic mode for SRAM ECC testing Mode by setting SFTY_DIAG.MEI[5:4] and SFTY_DIAG.DI[31:30] bits to 01
                                    B
mov r1, 0x5555_5555
sr r1, [SFTY_DIAG]
nop
nop
nop
Injection of a single bit error:
SFTY_PASSWD 		 equ A90
SFTY_DIAG 		   equ A92
VEC_ECC_CTRL 		equ 549
SFTY_ERROR_STATUS 	equ A94

//Set the password by setting SFTY_PASSWD.PWD[1:0] to 10
                                    B
mov r1, 0x2
sr r1, [SFTY_PASSWD]
//
//Enable diag mode and SRAM error injection. For Memory Error Injection, set SFTY_DIAG.MEI[5:4] bits to 10
                                    B and to enable diagnostic mode set SFTY_DIAG.DI[31:30] to 10
                                    B
mov r1, 0x9555_5565
sr r1, [SFTY_DIAG]
//
// Turn off ECC protection On VEC MEM by setting VEC_ECC_CTRL.DP[0] bit to 1
                                    B
mov r1, 0x1
sr r1, [VEC_ECC_CTRL]
//
// Get data from VEC MEM
mov r2, 0x90000000
ldb r1, [r2]
mov r4, r1
//
// Flip a single bit in the read data and store it back
bxor r1, r1, 1
st r1, [r2]
sync
// Turn on ECC by setting VEC_ECC_CTRL.DP[0] to 0
                                    B
mov r1, 0x0
sr r1, [VEC_ECC_CTRL]
//
// Read the corrupted data. The bit flip should be corrected
ld r1, [r2]
sync
//
// Corrected data should be same as original data
cmp r4, r1
jnz failed
//
// Check SFTY_ERROR_STATUS.DI-SBE0[11] bit in safety error status register
mov r5, 0x800
lr r6, [SFTY_ERROR_STATUS]
cmp r5, r6
jz passed
jnz failed
//
//Set the password by setting SFTY_PASSWD.PWD[1:0] to 10
                                    B
mov r0, 0x2
sr r0, [SFTY_PASSWD]
//
//Disable Diagnostic mode for SRAM ECC testing Mode by setting SFTY_DIAG.MEI[5:4] and SFTY_DIAG.DI[31:30] bits to 01
                                    B
mov r1, 0x5555_5555
sr r1, [SFTY_DIAG]
nop
nop
nop
Fault injection example for SM[HW]:PPU:CSM_ERROR_CORRECTION
Injection of a double bit error:
SFTY_PASSWD 		 equ A90
SFTY_DIAG 		   equ A92
CSM_ECC_CTRL 		equ 9A1
SFTY_ERROR_STATUS 	equ A94

//Set the password by setting SFTY_PASSWD.PWD[1:0] to 10
                                    B
mov r1, 0x2
sr r1, [SFTY_PASSWD]
//
//Enable diag mode and SRAM error injection. For Memory Error Injection, set SFTY_DIAG.MEI[5:4] bits to 10
                                    B and to enable diagnostic mode set SFTY_DIAG.DI[31:30] to 10
                                    B
mov r1, 0x9555_5565
sr r1, [SFTY_DIAG]
//
// Turn off ECC protection and disable exceptions on CSM by setting CSM_ECC_CTRL.DPL[0] bit to 1
                                    B and CSM_ECC_CTRL.DXL[1] bit to 1
                                    B
mov r1, 0x3
sr r1, [CSM_ECC_CTRL]
// Get data from CSM
mov r2, [CSM_ADDR]
ldb r1, [r2]
mov r4, r1
// Flip two bits in the read data and store it back
bxor r1, r1, 1
mov r3, r1
bxor r3, r3, 2
stb r3, [r2]
sync
// Turn on ECC by setting CSM_ECC_CTRL.DPL[0] to 0
                                    B
mov r1, 0x2
sr r1, [CSM_ECC_CTRL]
nop
nop
nop
nop
// Read the corrupted data
ld r1, [r2]
sync
nop
nop
nop
// Data should not be same as original data
cmp r4, r1
jz failed
// Check if SFTY_ERROR_STATUS.CPU[0] bit asserted
mov r5, 0x1
lr r6, [SFTY_ERROR_STATUS]
cmp r5, r6
jz passed
jnz failed
//
//Set the password by setting SFTY_PASSWD.PWD[1:0] to 10
                                    B
mov r0, 0x2
sr r0, [SFTY_PASSWD]
//Disable Diagnostic mode for SRAM ECC testing Mode by setting SFTY_DIAG.MEI[5:4] and SFTY_DIAG.DI[31:30] bits to 01
                                    B
mov r1, 0x5555_5555
sr r1, [SFTY_DIAG]
nop
nop
nop
Injection of a single bit error:
SFTY_PASSWD 		 equ A90
SFTY_DIAG 		   equ A92
CSM_ECC_CTRL 		equ 9A1
SFTY_ERROR_STATUS 	equ A94

//Set the password by setting SFTY_PASSWD.PWD[1:0] to 10

                                    B
mov r1, 0x2
sr r1, [SFTY_PASSWD]
//
//Enable diag mode and SRAM error injection. For Memory Error Injection, set SFTY_DIAG.MEI[5:4] bits to 10
                                    B and to enable diagnostic mode set SFTY_DIAG.DI[31:30] to 10
                                    B
mov r1, 0x9555_5565
sr r1, [SFTY_DIAG]
//
// Turn off ECC protection by setting CSM_ECC_CTRL.DPL[0] bit to 1
                                    B
mov r1, 0x1
sr r1, [CSM_ECC_CTRL]
// Get data from CSM
mov r2, [CSM_ADDR]
ldb r1, [r2]
mov r4, r1
// Flip a single bit in the read data and store it back
bxor r1, r1, 1
st r1, [r2]
sync
// Turn on ECC by setting CSM_ECC_CTRL.DPL[0] to 0
                                    B
mov r1, 0x0
sr r1, [CSM_ECC_CTRL]
//
// Read the corrupted data. The bit flip should be corrected
ld r1, [r2]
sync
//
//Corrected Data should be same as original data
cmp r4, r1
jnz failed
//
// Check SFTY_ERROR_STATUS.DI-SBE0[11] bit in safety error status register
mov r5, 0x800
lr r6, [SFTY_ERROR_STATUS]
cmp r5, r6
jz passed
jnz failed
//
//Set the password by setting SFTY_PASSWD.PWD[1:0] to 10
                                    B
mov r0, 0x2
sr r0, [SFTY_PASSWD]
//
//Disable Diagnostic mode for SRAM ECC testing Mode by setting SFTY_DIAG.MEI[5:4] and SFTY_DIAG.DI[31:30] bits to 01
                                    B
mov r1, 0x5555_5555
sr r1, [SFTY_DIAG]
nop
nop
nop
Fault injection example for SM[HW]:PPU:ICACHE_ERROR_CORRECTION
Injection of a double bit error:
SFTY_PASSWD		 equ A90
SFTY_DIAG		   equ A92
ERP_CTRL		    equ 3F
SFTY_ERROR_STATUS	equ A94
IC_CTRL			equ 11
IC_DATA			equ 1D
IC_RAM_ADDR		equ 1A

//Set the password by setting SFTY_PASSWD.PWD[1:0] to 10
                                    B
mov r1, 0x2
sr r1, [SFTY_PASSWD]
//
//Enable diag mode and SRAM error injection. For Memory Error Injection, set SFTY_DIAG.MEI[5:4] bits to 10
                                    B and to enable diagnostic mode set SFTY_DIAG.DI[31:30] to 10

                                    B
mov r1, 0x9555_5565
sr r1, [SFTY_DIAG]
//
// Turn off ECC protection and disable exceptions on DMP by setting ERP_CTRL.DPI[0] bit to 1
                                    B and ERP_CTRL.DXI[2] bit to 1
                                    B
mov r1, 0x5
sr r1, [ERP_CTRL]
// Read data from ICache through Aux interface
mov r2, 0x30000000 // ICache address
sr 0x20, [IC_CTRL] // Set to cache-controlled mode
sr r2, [IC_RAM_ADDR]
lr r1, [IC_DATA]
mov r4, r1
// Flip two bits in the read data and store it back
bxor r1, r1, 1
mov r3, r1
bxor r3, r3, 2
sr r3, [IC_DATA]
sync
// Turn on ECC by setting ERP_CTRL.DPI[0] to 0
                                    B
mov r1, 0x4
sr r1, [ERP_CTRL]
nop
nop
nop
nop
// Read the corrupted data
sr r2, [IC_RAM_ADDR]
lr r1, [IC_DATA]
sync
nop
nop
nop
// Data should not be same as original data
cmp r4, r1
jz failed
// Check if SFTY_ERROR_STATUS.CPU[0] bit asserted
mov r5, 0x1
lr r6, [SFTY_ERROR_STATUS]
cmp r5, r6
jz passed
jnz failed
//
//Set the password by setting SFTY_PASSWD.PWD[1:0] to 10

                                    B
mov r0, 0x2
sr r0, [SFTY_PASSWD]
//Disable Diagnostic mode for SRAM ECC testing Mode by setting SFTY_DIAG.MEI[5:4] and SFTY_DIAG.DI[31:30] bits to 01
                                    B
mov r1, 0x5555_5555
sr r1, [SFTY_DIAG]
nop
nop
nop
Injection of a single bit error:
SFTY_PASSWD 		 equ A90
SFTY_DIAG 		   equ A92
ERP_CTRL 		    equ 3F
SFTY_ERROR_STATUS 	equ A94
IC_CTRL 			equ 11
IC_DATA 			equ 1D
IC_RAM_ADDR 		 equ 1A

//Set the password by setting SFTY_PASSWD.PWD[1:0] to 10

                                    B
mov r1, 0x2
sr r1, [SFTY_PASSWD]
//
//Enable diag mode and SRAM error injection. For Memory Error Injection, set SFTY_DIAG.MEI[5:4] bits to 10
                                    B and to enable diagnostic mode set SFTY_DIAG.DI[31:30] to 10
                                    B
mov r1, 0x9555_5565
sr r1, [SFTY_DIAG]
//
// Turn off ECC protection DMP by setting ERP_CTRL.DPI[0] bit to 1
                                    B
mov r1, 0x1
sr r1, [ERP_CTRL]
// Read data from ICache through Aux interface
mov r2, 0x30000000 // ICache address
sr 0x20, [IC_CTRL] // Set to cache-controlled mode
sr r2, [IC_RAM_ADDR]
lr r1, [IC_DATA]
mov r4, r1
// Flip single bits in the read data and store it back
bxor r1, r1, 1
sr r3, [IC_DATA]
sync
// Turn on ECC by setting ERP_CTRL.DPI[0] to 0
                                    B
mov r1, 0x0
sr r1, [ERP_CTRL]
// Read the corrupted data. The bit flip should be corrected
sr r2, [IC_RAM_ADDR]
lr r1, [IC_DATA]
sync
nop
nop
nop
// Corrected Data should be the same as original data
cmp r4, r1
jnz failed
// Check SFTY_ERROR_STATUS.DI-SBE0[11] bit in safety error status register
mov r5, 0x800
lr r6, [SFTY_ERROR_STATUS]
cmp r5, r6
jz passed
jnz failed
//
//Set the password by setting SFTY_PASSWD.PWD[1:0] to 10
                                    B
mov r0, 0x2
sr r0, [SFTY_PASSWD]
//Disable Diagnostic mode for SRAM ECC testing Mode by setting SFTY_DIAG.MEI[5:4] and SFTY_DIAG.DI[31:30] bits to 01
                                    B
mov r1, 0x5555_5555
sr r1, [SFTY_DIAG]
nop
nop
nop
Fault injection example for SM[HW]:PPU:DCACHE_ERROR_CORRECTION
Injection of a double bit error:
SFTY_PASSWD 		 equ A90
SFTY_DIAG 		   equ A92
ERP_CTRL 		    equ 3F
SFTY_ERROR_STATUS 	equ A94

//Set the password by setting SFTY_PASSWD.PWD[1:0] to 10

                                    B
mov r1, 0x2
sr r1, [SFTY_PASSWD]
//
//Enable diag mode and SRAM error injection. For Memory Error Injection, set SFTY_DIAG.MEI[5:4] bits to 10
                                    B and to enable diagnostic mode set SFTY_DIAG.DI[31:30] to 10

                                    B
mov r1, 0x9555_5565
sr r1, [SFTY_DIAG]
//
// Turn off ECC protection and disable exceptions on DMP by setting ERP_CTRL.DPD[1] bit to 1
                                    B and ERP_CTRL.DXD[3] bit to 1

                                    B
mov r1, 0xA
sr r1, [ERP_CTRL]
// Get data from DCache
mov r2, 0x30000000
ldb r1, [r2]
mov r4, r1
//
// Flip two bits in the read data and store it back
bxor r1, r1, 1
mov r3, r1
bxor r3, r3, 2
stb r3, [r2]
sync
// Turn on ECC by setting ERP_CTRL.DPD[1] to 0
                                    B
mov r1, 0x8
sr r1, [ERP_CTRL]
nop
nop
nop
nop
// Read the corrupted data
ld r1, [r2]
sync
nop
nop
nop
// Data should not be same as original data
cmp r4, r1
jz failed
// Check if SFTY_ERROR_STATUS.CPU[0] bit asserted
mov r5, 0x1
lr r6, [SFTY_ERROR_STATUS]
cmp r5, r6
jz passed
jnz failed
//Set the password by setting SFTY_PASSWD.PWD[1:0] to 10

                                    B
mov r0, 0x2
sr r0, [SFTY_PASSWD]
//Disable Diagnostic mode for SRAM ECC testing Mode by setting SFTY_DIAG.MEI[5:4] and SFTY_DIAG.DI[31:30] bits to 01
                                    B
mov r1, 0x5555_5555
sr r1, [SFTY_DIAG]
nop
nop
nop
Injection of a single bit error:
SFTY_PASSWD 		 equ A90
SFTY_DIAG 		   equ A92
ERP_CTRL 		    equ 3F
SFTY_ERROR_STATUS 	equ A94

//Set the password by setting SFTY_PASSWD.PWD[1:0] to 10
                                    B
mov r1, 0x2
sr r1, [SFTY_PASSWD]
//
//Enable diag mode and SRAM error injection. For Memory Error Injection, set SFTY_DIAG.MEI[5:4] bits to 10
                                    B and to enable diagnostic mode set SFTY_DIAG.DI[31:30] to 10

                                    B
mov r1, 0x9555_5565
sr r1, [SFTY_DIAG]
//
// Turn off ECC protection by setting ERP_CTRL.DPD[1] bit to 1

                                    B
mov r1, 0x2
sr r1, [ERP_CTRL]
// Get data from DCache
mov r2, 0x30000000
ldb r1, [r2]
mov r4, r1
//
// Flip a single bit in the read data and store it back
bxor r1, r1, 1
st r1, [r2]
sync
// Turn on ECC by setting ERP_CTRL.DPD[1] to 0
                                    B
mov r1, 0x0
sr r1, [ERP_CTRL]
nop
nop
nop
nop
// Read the corrupted data. Bit flip should be corrected
ld r1, [r2]
sync
nop
nop
nop
// Corrected Data should be same as original data
cmp r4, r1
jnz failed
// Check SFTY_ERROR_STATUS.DI-SBE0[11] bit in safety error status register
mov r5, 0x800
lr r6, [SFTY_ERROR_STATUS]
cmp r5, r6
jz passed
jnz failed
//
//Set the password by setting SFTY_PASSWD.PWD[1:0] to 10

                                    B
mov r0, 0x2
sr r0, [SFTY_PASSWD]
//Disable Diagnostic mode for SRAM ECC testing Mode by setting SFTY_DIAG.MEI[5:4] and SFTY_DIAG.DI[31:30] bits to 01

                                    B
mov r1, 0x5555_5555
sr r1, [SFTY_DIAG]
nop
nop
nop
- IFX.Version: 2
- ReqIF-WF.Type: Information

### YPVA-EIAF-IDEF-DGHC: Relationship to ISO 26262
The AURIX™ TC43x is intended to be used as an element of an electrical and/or electronic (E/E) system as defined by the ISO 26262 set of standards. It was developed as a safety element out of context in accordance with the ISO 26262.
The scope of the safety element out of context comprises:
- The AURIX™ TC43x microcontroller hardware component including its firmware.
- Assumptions of use related to the hardware environment including assumed external safety mechanisms.
- Assumptions of use related to the software elements that Support the integration of the AURIX™ TC43x microcontroller hardware components in a safety related application.
- Assumptions of use related to the software environment.
- Assumptions of use related to the use of the safety mechanisms provided by the safety element out of context.
This document is part of the safety documentation according to ISO 26262:2018 Part 11 and collects the following information:
- The description of the microcontroller safety architecture with an abstract description of microcontroller functionality and description of safety mechanisms.
- The description of Assumptions of Use of the microcontroller with respect to its intended use.
- The description of the microcontroller configuration and related hardware and/or software procedures to control a fault after its detection.
Completing the actions described in this document will only satisfy some of the requirements defined by ISO 26262:2018 for safety-related applications. It is the integrator’s responsibility to satisfy the full requirements of the ISO 26262:2018, for usage of the AURIX™ TC43x microcotroller in safety-related applications.
This document targets the highest functional safety integrity level for the assumed safety requirements related to this safety element out of context. For functional safety goals which do not require high functional safety integrity levels as assumed here, system integrators will need to tailor the requirements for their specific application.
- IFX.Version: 4
- ReqIF-WF.Type: Information

### FYZA-FJGC-EGAF-FJHE: Safety related information for package
This chapter provides safety related information applicable for the package. For example, location of pins with sufficient physical separation are specified here.
This chapter is under construction.
- IFX.Version: 3
- ReqIF-WF.Type: Information

## EXGA-FEBJ-IICE-DHBG: References
1. AURIX™ TC43x User Manual, latest version
2. AURIX™ TC43x Datasheet, latest version
3. AURIX™ TC43x FMEDA sheet, latest version
4. AURIX™ TC43x safety analysis summary report (SASR), latest version
5. ISO 26262, Road Vehicles Functional Safety, 2018 second edition
- IFX.Version: 2
- ReqIF-WF.Type: Information

## JRTA-FCBC-GGBD-AAAH
PRDCFG
PRDCFG
- ReqIF-WF.Type: Information

## DEBA-FJGJ-JCDC-EDFG
TLSR Use Case (TUC)
TUC
- ReqIF-WF.Type: Information

## WEUA-FJHA-BBGC-IFBA
Safety Mechanism (SM)
SM
- ReqIF-WF.Type: Information

## QFHA-EFJG-GAHG-BEDH
Inter-Integrated circuit (I2C)
I2C
- ReqIF-WF.Type: Information

## ZKLA-EEGI-ICIA-HHDI
direct memory access (DMA)
DMA
- ReqIF-WF.Type: Information

## YBXA-EFBH-DGCH-HBEI
vector digital signal processing unit (VDSP)
VDSP
- ReqIF-WF.Type: Information

## MZVA-FABI-EJBH-GBDD
Software (SW)
SW
- ReqIF-WF.Type: Information

## EEXA-FCBB-ABJF-GDJG
parallel processing unit (PPU)
PPU
- ReqIF-WF.Type: Information

## ZKHA-EEHF-JBFC-BFFC
safety and security alarm management unit (SMU)
SMU
- ReqIF-WF.Type: Information

## NKDA-FCBA-DAHE-GIBE
single bit error (SBE)
SBE
- ReqIF-WF.Type: Information

## GUGA-EFJD-AAIJ-FBEC
flexible peripheral interconnect (FPI)
FPI
- ReqIF-WF.Type: Information

## DDXA-FJHA-BBGE-IICD
External Safety Mechanism (ESM)
ESM
- ReqIF-WF.Type: Information

## DADA-EEHF-IFBH-JACE
high speed serial link (HSSL)
HSSL
- ReqIF-WF.Type: Information

## ZZQA-EEFG-JGEC-FFBA
Low Latency Interconnect (LLI)
LLI
- ReqIF-WF.Type: Information

## MGVA-EFJG-EGDI-GAIA
Flexray controller (ERAY)
ERAY
- ReqIF-WF.Type: Information

## XRSA-EFJG-FIDC-CGBC
Queued synchronous peripheral interface (QSPI)
QSPI
- ReqIF-WF.Type: Information

## RGEA-EEHC-CICC-BBIF
shared resource interconnect (SRI)
SRI
- ReqIF-WF.Type: Information

## AXIA-EFJG-GCCI-ECAJ
external request unit (ERU)
ERU
- ReqIF-WF.Type: Information

## DLKA-FJGJ-JJCD-IFEC
Assumption of Use (AoU)
AoU
- ReqIF-WF.Type: Information

## ZGEA-FABI-FEDE-FIBJ
software over the air (SOTA)
SOTA
- ReqIF-WF.Type: Information

## HXIA-FCED-BECE-IHHC
fault detection time interval (FDTI)
FDTI
- ReqIF-WF.Type: Information

## KJGA-EFBA-DDGJ-IFCJ
distributed LMU (DLMU)
DLMU
- ReqIF-WF.Type: Information

## IDKA-EEGI-IEHH-HCDG
local memory unit (LMU)
LMU
- ReqIF-WF.Type: Information

## CPGA-FABI-FEDH-FEGD
lockstep (LS)
LS
- ReqIF-WF.Type: Information

## NEKA-EFBA-DDHD-DCIG
program scratch pad ram (PSPR)
PSPR
- ReqIF-WF.Type: Information

## IAJA-EEHC-DGCD-IDJC
Error correction code (ECC)
ECC
- ReqIF-WF.Type: Information

## BWVA-FABI-EJBF-JIFA
Hardware (HW)
HW
- ReqIF-WF.Type: Information

## JWEA-FCBI-IJBD-CGJB
single-point fault metric (SPFM)
SPFM
- ReqIF-WF.Type: Information

## JOWA-FJGF-AJGI-FBDH
totally self checking (TSC)
TSC
- ReqIF-WF.Type: Information

## KSYA-EFBA-DDBF-GCEC
data scratch pad ram (DSPR)
DSPR
- ReqIF-WF.Type: Information

## CDYA-EFBG-HHFJ-JBED
asynchronous synchronous interface (ASCLIN)
ASCLIN
- ReqIF-WF.Type: Information

## XAYA-EEGI-IGFE-CAGD
interrupt router (IR)
IR
- ReqIF-WF.Type: Information

## UKAA-EFCG-IFGC-IBED
Automotive safety integrity level (ASIL)
ASIL
- ReqIF-WF.Type: Information

## BMYA-EFJE-AEFC-HAAD
Gigabit ethernet (GETH)
GETH
- ReqIF-WF.Type: Information

## SJEA-FCBI-IJHB-CDII
latent fault metric (LFM)
LFM
- ReqIF-WF.Type: Information

## PTPA-FJGJ-JCBA-IIFI
Top Level Safety Requirements (TLSR)
TLSR
- ReqIF-WF.Type: Information

## GGNA-EFBG-FACE-GADH
analog to digital converter (ADC)
ADC
- ReqIF-WF.Type: Information

## FPDA-EFJG-GDHF-GCJB
generic timer module (GTM)
GTM
- ReqIF-WF.Type: Information

## XJAA-EEHC-DIDA-CJBE
non-volatile memory (NVM)
NVM
- ReqIF-WF.Type: Information

## OBXA-EFJG-GCCJ-JAJJ
system control unit (SCU)
SCU
- ReqIF-WF.Type: Information

## CHLA-EFCD-CHBB-GHCF
error detection code (EDC)
EDC
- ReqIF-WF.Type: Information

## UDAA-EFBG-EDEI-FGAI
central processing unit (CPU)
CPU
- ReqIF-WF.Type: Information

## VQDA-EEGI-IFGC-AHDJ
peripheral component interconnect express (PCIe)
PCIe
- ReqIF-WF.Type: Information

## MDDA-FCBA-DBBA-DHIH
double bit error (DBE)
DBE
- ReqIF-WF.Type: Information

## HZEA-EFBJ-GBED-DCJJ
controller area network (CAN)
CAN
- ReqIF-WF.Type: Information

## SSPA-FJHJ-BFBF-IADD
Functional Block (FB)
FB
- ReqIF-WF.Type: Information

## NBNA-EEIH-IGHH-FBGI
system mode management (SMM)
SMM
- ReqIF-WF.Type: Information

## FCCA-EFCD-CICC-JADB
cyclic redundancy check (CRC)
CRC
- ReqIF-WF.Type: Information

## ULPA-FJFH-CGDE-IGJH
Safety Element out of Context (SEooC)
SEooC
- ReqIF-WF.Type: Information

## OBJA-EFBF-FAEE-FJFI
program flash (PFLASH)
PFLASH
- ReqIF-WF.Type: Information

## BJVA-FJGJ-JAFI-JICF
Microcontroller Unit (MCU)
MCU
- ReqIF-WF.Type: Information

## EIHA-FCBB-ADDF-CDCH
diagnostic test time interval (DTTI)
DTTI
- ReqIF-WF.Type: Information

## RURA-FEBA-JJFI-BHGB: Revision history
| Document version | Date of release | Description of changes |
| --- | --- | --- |
| 0.4 | 01.08.202 | First DRAFT release |
- IFX.Version: 2
- ReqIF-WF.Type: Information
